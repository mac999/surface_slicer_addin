Attribute VB_Name = "GlobalVars"
Option Explicit

Public g_oCivilApp As AeccApplication       'Civil3D 어플리케이션 객체 전역 변수 선언
Public g_oDocument As AeccDocument  '도면 객체 변수 선언
Public g_oDatabase As AeccDatabase      '데이터베이스 객체 변수 선언

' 위 세개 전역 변수를 설정하는 GetGlobalCivilObjects() 함수를 만든다.
'
Function GetGlobalCivilObjects() As Boolean
    Dim oAcadApp As AcadApplication
    Set oAcadApp = ThisDrawing.Application
    ' Civil3D 버전 번호를 주의해야 한다. 여기서 번호 10은 Civil3d 2013 버전 객체이다.
    Const sAppName = "AeccXUiLand.AeccApplication.10.0"
    Set g_oCivilApp = oAcadApp.GetInterfaceObject(sAppName)
    If (g_oCivilApp Is Nothing) Then
        MsgBox "Error creating " & sAppName & ", exit."
        GetGlobalCivilObjects = False
        Exit Function
    End If
    Set g_oDocument = g_oCivilApp.ActiveDocument
    Set g_oDatabase = g_oDocument.Database
    GetGlobalCivilObjects = True            '성공적으로 설정하였으면 True를 리턴한다.
End Function
