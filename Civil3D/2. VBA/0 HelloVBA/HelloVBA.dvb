Attribute VB_Name = "HelloVBA"
Public Sub Hello()
    Dim oAcadApp As AcadApplication
    Set oAcadApp = ThisDrawing.Application
    
    '어플리케이션 컴포넌트 인터페이스를 얻는다. 버전은 설치된 Civil3D에 따라 다르다.
    Const sCivilAppName = "AeccXUiLand.AeccApplication.10.0"
    Dim oCivilApp As AeccApplication
    Set oCivilApp = oAcadApp.GetInterfaceObject(sCivilAppName)
    
    '어플리케이션에서 현재 활성화된 도면 객체를 얻는다.
    Dim oDocument As AeccDocument
    Set oDocument = oCivilApp.ActiveDocument        '현재 활성화된 도면 획득
    oCivilApp.ZoomExtents                               '현재 활성화된 도면 최대 줌 수행
End Sub
