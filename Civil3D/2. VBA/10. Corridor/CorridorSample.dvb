Attribute VB_Name = "BaseObjects"
'
' MODULE_ID {BaseObjects.bas}
' {CorridorSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

Public g_oCivilApp As AeccRoadwayApplication
Public g_oRoadwayDocument As AeccRoadwayDocument
Public g_oRoadwayDatabase As AeccRoadwayDatabase


'
' Start Civil 3D and create Civil 3D document and database objects
' for use with corridor objects.
'
Function GetBaseCivilObjects() As Boolean
    Dim oApp As AcadApplication
    Set oApp = ThisDrawing.Application
    ' NOTE - Always specify the version number.
    Const sAppName = "AeccXUiRoadway.AeccRoadwayApplication.10.0"
    Set g_oCivilApp = oApp.GetInterfaceObject(sAppName)
    If (g_oCivilApp Is Nothing) Then
        MsgBox "Error creating " & sAppName & ", exit."
        GetBaseCivilObjects = False
        Exit Function
    End If
    Set g_oRoadwayDocument = g_oCivilApp.ActiveDocument
    Set g_oRoadwayDatabase = g_oRoadwayDocument.Database
    GetBaseCivilObjects = True
End Function

Attribute VB_Name = "Corridor"
'
' MODULE_ID {Corridor.bas}
' {CorridorSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


' For use by the functions that output data to
' Microsoft Word.
Dim oPara As Word.Paragraph



'
' Demonstrate reading and setting some roadway
' specific ambient settings.
'
Public Function SetAmbientSettings() As Boolean
    ' Get a reference to the root settings object, casting
    ' it to the AeccRoadwaySettingsRoot type in the
    ' process.
    Dim oRoadwaySettings  As AeccRoadwaySettingsRoot
    Set oRoadwaySettings = g_oRoadwayDocument.Settings
    
    ' Set corridor-specific settings.
    Debug.Print oRoadwaySettings.CorridorSettings.CorridorSurfaceNameTemplate
    oRoadwaySettings.CorridorSettings.NameTemplate = "Corridor <[Next Counter(CP)]> (<[Corridor First Assembly(CP)]>)"
    oRoadwaySettings.CorridorSettings.CorridorSurfaceNameTemplate = "New surface"
    
    Dim oSettingsCorridor As AeccSettingsCorridor
    Set oSettingsCorridor = oRoadwaySettings.CorridorSettings
    Dim sName As String
    sName = g_oRoadwayDocument.AlignmentStyles.Item(0).Name
    oSettingsCorridor.StyleSettings.AlignmentStyle.Value = sName
 
    ' Set assembly-specific settings.
    Debug.Print oRoadwaySettings.AssemblySettings.OffsetNameTemplate
    oRoadwaySettings.AssemblySettings.OffsetNameTemplate = "Offset "
    
    ' Get subassembly-specific setting.
    Debug.Print oRoadwaySettings.SubassemblySettings.CodeSetStyle.Value
    
    ' Get quantity takeoff-specific setting.
    Debug.Print oRoadwaySettings.QuantityTakeoffSettings.QuantityTakeoffCriteria.Value

    ' Function completed successfully.
    SetAmbientSettings = True
End Function


'
' Create a new corridor.
'
Public Function CreateCorridor() As Boolean
    ' To create a corridor, we need to create the alignment
    ' and profile that the corridor will follow and the
    ' assembly that the corridor will be constructed with.
    
    '''''''''''''''''''''''''''''''''''''''''''''''''''''
    ' Create a simple allignment using layout methods.
    
    ' First, we will get the collection of alignments
    ' not in a site.
    Dim oAlignments As AeccAlignmentsSiteless
    Set oAlignments = g_oRoadwayDocument.AlignmentsSiteless

    ' Create the alignment only if it has not already been created.
    Dim oAlignment As AeccAlignment
    On Error Resume Next
    Set oAlignment = oAlignments.Item(ALIGNMENT_NAME)
    On Error GoTo 0
    If (oAlignment Is Nothing) Then
        ' Get the default alignment style and alignment label
        ' style set.
        Dim sStyleName As String
        Dim sLabelSetName As String
        sStyleName = g_oRoadwayDocument.AlignmentStyles.Item(0).Name
        sLabelSetName = g_oRoadwayDocument.AlignmentLabelStyleSets.Item(0).Name
        
        ' Add a blank alignment with our style sets to the
        ' collection of alignments.
        Set oAlignment = oAlignments.Add(ALIGNMENT_NAME, "0", sStyleName, sLabelSetName)
        If (oAlignment Is Nothing) Then
            Debug.Print "Error creating alignment: " & Err.Description & " - " & Err.Number
            Err.Clear
            ThisDrawing.Application.ZoomExtents
            CreateCorridor = False
            Exit Function
        End If
    
        ' Add layout entities to the currently empty alignment.
        Dim dPoint1(0 To 2) As Double
        Dim dPoint2(0 To 2) As Double
        Dim dRadius As Double
        Dim dLength As Double
        dPoint1(0) = 4932.4: dPoint1(1) = 4784.2: dPoint1(2) = 0
        dPoint2(0) = 5600.2: dPoint2(1) = 5550.9: dPoint2(2) = 0
        dRadius = 751.8
        dLength = 999.9
        
        Dim oAlignmentArc As AeccAlignmentArc
        Set oAlignmentArc = oAlignment.Entities.AddFixedCurve6(dPoint1, dPoint2, 751.8, True)
        Dim oAlignmentTangent As AeccAlignmentTangent
        Set oAlignmentTangent = oAlignment.Entities.AddFloatingLine2(oAlignmentArc.Id, dLength)
    End If


    '''''''''''''''''''''''''''''''''''''''''''''''''''''
    ' Create a profile along this alignment.
    
    ' Get the alignment's collection of profiles.
    Dim oProfiles As AeccProfiles
    On Error Resume Next
    Set oProfiles = oAlignment.Profiles
    On Error GoTo 0
    If (oProfiles Is Nothing) Then
        Debug.Print "Error accessing profiles collection."
        CreateCorridor = False
        Exit Function
    End If

    ' Create the profile only if it has not already been created.
    Dim oProfile As AeccProfile
    On Error Resume Next
    Set oProfile = oProfiles.Item(PROFILE_NAME)
    On Error GoTo 0
    If (oProfile Is Nothing) Then
        ' Get the default profile style.
        Dim sProfileStyleName As String
        sProfileStyleName = g_oRoadwayDocument.LandProfileStyles.Item(0).Name

        Set oProfile = oProfiles.Add(PROFILE_NAME, aeccFinishedGround, sProfileStyleName)
        ' Now we will add the entities that define the
        ' profile.
        ' NOTE: Profile entity points are not x,y,z point, but
        ' station-elevation locations.
        Dim dLoc1(0 To 1) As Double
        Dim dLoc2(0 To 1) As Double
        Dim oProfileTangent1 As aeccProfileTangent
        dLoc1(0) = oAlignment.StartingStation: dLoc1(1) = 0#
        dLoc2(0) = 758.2: dLoc2(1) = 4.37
        Set oProfileTangent1 = oProfile.Entities.AddFixedTangent(dLoc1, dLoc2)
        Dim oProfileTangent2 As aeccProfileTangent
        dLoc1(0) = 1208.2: dLoc1(1) = 12.55
        dLoc2(0) = oAlignment.EndingStation: dLoc2(1) = -10#
        Set oProfileTangent2 = oProfile.Entities.AddFixedTangent(dLoc1, dLoc2)
        
        Dim dCrestLen As Double
        dCrestLen = 1208.2 - 758.2
        Call oProfile.Entities.AddFreeSymmetricParabolaByLength(oProfileTangent1.Id, oProfileTangent2.Id, aeccCrest, dCrestLen, True)

        oProfile.Update
    End If


    '''''''''''''''''''''''''''''''''''''''''''''''''''''
    ' Get an assembly for the corridor.
    
    ' Get a reference to the assemblies collection.
    Dim oAssemblies As AeccAssemblies
    On Error Resume Next
    Set oAssemblies = g_oRoadwayDocument.Assemblies
    On Error GoTo 0
    If (oAssemblies Is Nothing) Then
        MsgBox "Error accessing assemblies collection."
        CreateCorridor = False
        Exit Function
    End If

    ' Get the first assembly.  We cannot create
    ' assemblies through the API - at least one must
    ' already exist in the drawing.
    Dim oAssembly As AeccAssembly
    On Error Resume Next
    Set oAssembly = oAssemblies.Item(0)
    On Error GoTo 0
    If (oAssembly Is Nothing) Then
        MsgBox "This sample requires an existing assembly in the current document."
        CreateCorridor = False
        Exit Function
    End If

    
    '''''''''''''''''''''''''''''''''''''''''''''''''''''
    ' Create the corridor.

    ' Add a new corridor to the document.
    
    Dim oCorridors As AeccCorridors
    ' Note: You will get an invalid parameter error here
    ' if the document has no corridors.
    On Error Resume Next
    Set oCorridors = g_oRoadwayDatabase.Corridors
    On Error GoTo 0
    MsgBox g_oRoadwayDatabase.Corridors.Count

    Dim oCorridor As AeccCorridor
    Set oCorridor = oCorridors.Add(CORRIDOR_NAME, oAlignment.Name, oProfile.Name, oAssembly.Name)
    
    ''''''''''''''''''''''''''''''''''''''''''''''''''''''
    ' Note that we can only create a simple corridor
    ' without building it. Users have to go into the
    ' property pages in order to set the targets for
    ' the assembly and then build the corridor.
    ''''''''''''''''''''''''''''''''''''''''''''''''''''''
    
    
    ' With an alternate alignment and profile we can
    ' add new baselines to the corridor.  It would
    ' look something like the following:
    'Set oBaseline = oCorridor.AddBaseline(oAlignment2.Name, oProfile2.Name, oAssembly.Name)
    
    
    CreateCorridor = True
End Function


'
' Display information about all assemblies in
' the current document in Word.  Word or a
' product that uses Word (such as Microsoft
' Outlook) must be running for this to work.
'
Public Function ListAssembliesToWord() As Boolean
    ' Error check the existence of global variables.
    If (oPara Is Nothing) Then
        ListAssembliesToWord = False
        Exit Function
    End If

    ' Get a reference to the assemblies collection.
    Dim oAssemblies As AeccAssemblies
    On Error Resume Next
    Set oAssemblies = g_oRoadwayDocument.Assemblies
    On Error GoTo 0
    If (oAssemblies Is Nothing) Then
        MsgBox "There are no assemblies in this document."
        ListAssembliesToWord = False
        Exit Function
    End If
    
    ' Add the title to Word.
    oPara.Range.Text = "Number of Assemblies: " & oAssemblies.Count
    oPara.Range.Font.Bold = True
    oPara.Range.Font.Size = 14
    oPara.Range.Font.Name = "Courier New"
    oPara.Format.SpaceAfter = 24    '24 pt spacing after paragraph.
    oPara.Range.InsertParagraphAfter
   
    oPara.Range.Font.Bold = False
    oPara.Range.Font.Size = 10
    oPara.Format.SpaceAfter = 4
   
    ' Get the list of all assemblies in the current
    ' document.
    Dim oAssembly As AeccAssembly
    For Each oAssembly In oAssemblies
        oPara.Range.Text = "Assembly: " & oAssembly.Name
        oPara.Range.InsertParagraphAfter
        oPara.Range.Text = "Display name: " & oAssembly.DisplayName
        oPara.Range.InsertParagraphAfter
        oPara.Range.Text = "Code set style: " & oAssembly.CodeSetStyleName
        oPara.Range.InsertParagraphAfter
        oPara.Range.Text = ""
        oPara.Range.InsertParagraphAfter
    Next
    
    ' Function completed successfully.
    ListAssembliesToWord = True
End Function ' ListAssembliesToWord


'
' Go through all corridors in the current document and
' display information about its constiuent feature lines,
' baselines, assemblies, subassemblies, surfaces, and
' surface boundaries in Word. Word or a product that
' uses Word (such as Microsoft Outlook) must be running
' for this to work.
'
Public Function ListCorridorsToWord() As Boolean
    Dim X As Double
    Dim Y As Double
    Dim Z As Double

    ' Error check the existence of global variables.
    If (oPara Is Nothing) Then
        ListCorridorsToWord = False
        Exit Function
    End If

    ' Add the title to Word.
    oPara.Range.Text = "Corridors of " & g_oRoadwayDocument.Name
    oPara.Range.Font.Bold = True
    oPara.Range.Font.Size = 14
    oPara.Range.Font.Name = "Courier New"
    oPara.Format.SpaceAfter = 24    '24 pt spacing after paragraph.
    oPara.Range.InsertParagraphAfter
   
    oPara.Range.Font.Bold = False
    oPara.Range.Font.Size = 10
    oPara.Format.SpaceAfter = 4
   
    Dim oCorridors As AeccCorridors
    
    On Error Resume Next
    Set oCorridors = g_oRoadwayDocument.Corridors
    On Error GoTo 0
    If (oCorridors Is Nothing) Then
        MsgBox "Unable to access Corridors collection."
        ListCorridorsToWord = False
        Exit Function
    End If
    
    Dim oCorridor As AeccCorridor
    For Each oCorridor In oCorridors
        oPara.Range.Text = "Corridor: " & oCorridor.Name
        oPara.Range.InsertParagraphAfter
        
        ' oCorridor.Baselines , oCorridor.CorridorSurfaces
        Dim oBaseline As AeccBaseline
        For Each oBaseline In oCorridor.Baselines
            Debug.Print oBaseline.Alignment.Name
            Debug.Print oBaseline.profile.Name
            Debug.Print oBaseline.StartStation
            Debug.Print oBaseline.EndStation
            
        
            Dim oBaselineFeatureLines As AeccBaselineFeatureLines
            Set oBaselineFeatureLines = oBaseline.MainBaselineFeatureLines
            
            Dim oFeatureLinesCol As AeccFeatureLinesCol
            Set oFeatureLinesCol = oBaselineFeatureLines.FeatureLinesCol
            
            Dim oFeatureLines As AeccFeatureLines
            For Each oFeatureLines In oFeatureLinesCol
                oPara.Range.Text = ""
                oPara.Range.InsertParagraphAfter
                Dim sCodes As String
                sCodes = oFeatureLines.FeatureLineCodeInfo.CodeName
                oPara.Range.Text = "Feature lines for :"
                oPara.Range.InsertParagraphAfter
                oPara.Range.Text = "Num Feature lines: " & oFeatureLines.Count
                oPara.Range.InsertParagraphAfter
                Dim oFeatureLine As AeccFeatureLine
                For Each oFeatureLine In oFeatureLines
                    oPara.Range.Text = "  Feature Line code: " & oFeatureLine.CodeName
                    oPara.Range.InsertParagraphAfter
                    
                    ' To print out all point locations along the
                    ' feature lines, uncomment the following.  Doing
                    ' so is not recommended because of the very large
                    ' amount of information generated.
                    
                    'Dim oFeatureLinePoint As AeccFeatureLinePoint
                    'For Each oFeatureLinePoint In oFeatureLine.FeatureLinePoints
                    '    X = oFeatureLinePoint.XYZ(0)
                    '    Y = oFeatureLinePoint.XYZ(1)
                    '    Z = oFeatureLinePoint.XYZ(2)
                    '    oPara.Range.Text = "    Point: " & X & ", " & Y & ", " & Z
                    '    oPara.Range.InsertParagraphAfter
                    'Next ' Points in a feature line
                Next ' Feature lines
            Next ' Collections of feature lines
            
            Dim oBaselineRegion As AeccBaselineRegion
            For Each oBaselineRegion In oBaseline.BaselineRegions
                oPara.Range.Text = ""
                oPara.Range.InsertParagraphAfter
                oPara.Range.Text = "Baseline Region"
                oPara.Range.InsertParagraphAfter
                oPara.Range.Text = "Start station: " & oBaselineRegion.StartStation
                oPara.Range.InsertParagraphAfter
                oPara.Range.Text = "End station: " & oBaselineRegion.EndStation
                oPara.Range.InsertParagraphAfter
                
                ' Get a sorted list of all stations where a
                ' assembly cross section is placed.
                Dim v As Variant
                v = oBaselineRegion.GetSortedStations()
                Dim i As Integer
                Debug.Print
                Debug.Print "Assembly stations:"
                For i = 0 To UBound(v)
                    Debug.Print v(i)
                Next i
                Debug.Print
                
                ' Get a list of all additional stations.
                Dim dArray() As Double
                dArray = oBaselineRegion.GetAdditionalStations
                Debug.Print
                Debug.Print "Additional assembly stations:"
                For i = 0 To UBound(dArray)
                    Debug.Print dArray(i)
                Next i
                Debug.Print

                ' Demonstrate the baseline station manipulation
                ' methods.
                oBaselineRegion.AddStation 1234.5, "Station description"
                'oBaselineRegion.DeleteStation 1234.5
                
                ' Go through all the assemblies used in this baseline
                ' region.
                Dim oAppliedAssembly As AeccAppliedAssembly
                For Each oAppliedAssembly In oBaselineRegion.AppliedAssemblies
                    Dim lCount As Long
                    oPara.Range.Text = "  Applied Assembly"
                    oPara.Range.InsertParagraphAfter
                    lCount = oAppliedAssembly.GetLinks().Count
                    oPara.Range.Text = "  Num Links: " & lCount
                    oPara.Range.InsertParagraphAfter
                    lCount = oAppliedAssembly.GetPoints().Count
                    oPara.Range.Text = "  Num Points: " & lCount
                    oPara.Range.InsertParagraphAfter
                    lCount = oAppliedAssembly.GetShapes().Count
                    oPara.Range.Text = "  Num Shapes: " & lCount
                    oPara.Range.InsertParagraphAfter
                    oPara.Range.Text = ""
                    oPara.Range.InsertParagraphAfter
                    
                    ' To print out all information for each element
                    ' of the subassemblies, uncomment the following.
                    ' Doing so is not recommended because of the
                    ' very large amount of information generated.
                    
                    'Dim oShape As AeccCalculatedShape
                    'For Each oShape In oAppliedAssembly.GetShapes()
                    '    Dim dArea As Double
                    '    dArea = oShape.GetArea()
                    '    oPara.Range.Text = "    Shape"
                    '    oPara.Range.InsertParagraphAfter
                    '    oPara.Range.Text = "      Area              : " & dArea
                    '    oPara.Range.InsertParagraphAfter
                    '    oPara.Range.Text = "      # Calculated Links: " & oShape.CalculatedLinks.Count
                    '
                    '    oPara.Range.InsertParagraphAfter
                    '    Call DisplaySubassemblyInfoToWord(oShape.SubassemblyBelongedTo)
                    'Next ' oShape
                    '
                    'Dim oLink As AeccCalculatedLink
                    'For Each oLink In oAppliedAssembly.GetLinks()
                    '    oPara.Range.Text = "    Link"
                    '    oPara.Range.InsertParagraphAfter
                    '    oPara.Range.Text = "      Number of Calculated Points: " & oLink.CalculatedPoints.Count
                    '    oPara.Range.InsertParagraphAfter
                    'Next ' oLink
                    '
                    'Dim oPoint As AeccCalculatedPoint
                    'For Each oPoint In oAppliedAssembly.GetPoints()
                    '    Dim vPos As Variant
                    '    vPos = oPoint.GetStationOffsetElevationToBaseline()
                    '    oPara.Range.Text = "    Point"
                    '    oPara.Range.InsertParagraphAfter
                    '    oPara.Range.Text = "      Position:  Station = " & vPos(0) & "  Offset = " & vPos(1) & " Elevation = " & vPos(2)
                    '    oPara.Range.InsertParagraphAfter
                    'Next ' oPoint
                Next ' Applied assemblies
                
                
                ' Go through any offset baselines that might exist
                ' in this baseline region.
                Dim oBaseBaseline As IAeccBaseBaseline
                For Each oBaseBaseline In oBaselineRegion.OffsetBaselines
                    Dim dMainStart As Double ' station on main baseline
                    Dim dMainEnd As Double ' station on main baseline
                    Dim vOE As Variant

                    Select Case oBaseline.Type
                        Case aeccCorridorOffsetBaseline
                            Dim oOffsetBaseline As AeccOffsetBaseline
                            Set oOffsetBaseline = oBaseBaseline
                            
                            ' Report that an offset baseline exists.
                            dMainStart = oOffsetBaseline.StartStationOnMainBaseline
                            dMainEnd = oOffsetBaseline.EndStationOnMainBaseline
                            oPara.Range.Text = " - Offset baseline, station " & dMainStart & " to " & dMainEnd
                            oPara.Range.InsertParagraphAfter
                            
                            ' Report the offset of the baseline at its
                            ' start and its end.
                            vOE = oOffsetBaseline.GetOffsetElevationFromMainBaselineStation(dMainStart)
                            oPara.Range.Text = " - is offset by: " & vOE(0) & " horizontal and: " & vOE(1) & " vertical at start"
                            oPara.Range.InsertParagraphAfter
                            vOE = oOffsetBaseline.GetOffsetElevationFromMainBaselineStation(dMainEnd)
                            oPara.Range.Text = " - is offset by: " & vOE(0) & " horizontal and: " & vOE(1) & " vertical at end"
                            oPara.Range.InsertParagraphAfter
                        Case aeccCorridorHardcodedOffsetBaseline
                            oPara.Range.InsertParagraphAfter
                            Dim oHardcodedOffsetBaseline As AeccHardcodedOffsetBaseline
                            Set oHardcodedOffsetBaseline = oBaseBaseline

                            ' Report that a hardcoded offset baseline
                            ' exists.
                            dMainStart = oHardcodedOffsetBaseline.StartStation
                            dMainEnd = oHardcodedOffsetBaseline.EndStation
                            oPara.Range.Text = " - Hardcoded offset baseline, station " & dMainStart & " to " & dMainEnd

                            vOE = oHardcodedOffsetBaseline.OffsetElevationFromMainBaseline
                            oPara.Range.Text = " - is offset by: " & vOE(0) & " horizontal and: " & vOE(1) & " vertical"
                            oPara.Range.InsertParagraphAfter
                           
                            'Dim oBaselineFeatureLines As AeccBaselineFeatureLines
                            'oBaselineFeatureLines = oHardcodedOffsetBaseline.RelatedOffsetBaselineFeatureLines
                            ' Now we can use oBaselineFeatureLines.FeatureLinesCol collection.
                    End Select
                Next ' Offset baselines
            Next ' Baseline regions
        Next ' Baselines
        
        oPara.Range.Text = ""
        oPara.Range.InsertParagraphAfter
        oPara.Range.Text = ""
        oPara.Range.InsertParagraphAfter
        
        ''''''''''''''''''''''''''''''''''''''''''''''''''
        ' Display information on corridor surfaces.
        
        Dim oCorridorSurface As AeccCorridorSurface
        For Each oCorridorSurface In oCorridor.CorridorSurfaces
            oPara.Range.Text = "Surface: " & oCorridorSurface.Name
            oPara.Range.InsertParagraphAfter
            
            ' Get the elevation of the surface at a specific
            ' point.
            Dim dElev As Double
            dElev = oCorridorSurface.FindElevationAtXY(4400.5, 4000.7)
            oPara.Range.Text = "Elevation at 4400.5, 4000.7: " & dElev
            oPara.Range.InsertParagraphAfter
            
            ' Get the feature line, link, and point codes
            ' that were used to construct this surface.
            Dim sCodeArray() As String
            Dim sCodeList As String
            sCodeArray = oCorridorSurface.FeatureLineCodes
            For i = 0 To UBound(sCodeArray)
                sCodeList = sCodeList & " " & sCodeArray(i)
            Next i
            oPara.Range.Text = "Feature line codes: " & sCodeList
            oPara.Range.InsertParagraphAfter
            
            sCodeArray = oCorridorSurface.LinkCodes
            For i = 0 To UBound(sCodeArray)
                sCodeList = sCodeList & " " & sCodeArray(i)
            Next i
            oPara.Range.Text = "Link codes: " & sCodeList
            oPara.Range.InsertParagraphAfter
            
            sCodeArray = oCorridorSurface.PointCodes
            For i = 0 To UBound(sCodeArray)
                sCodeList = sCodeList & " " & sCodeArray(i)
            Next i
            oPara.Range.Text = "Point codes: " & sCodeList
            oPara.Range.InsertParagraphAfter
            
            Dim vPoints As Variant
            Dim oFeatureLineComponent As AeccFeatureLineComponent

            ' For each surface, display information about
            ' the surface's boudnary.
            Dim oCorridorSurfaceBoundary As AeccCorridorSurfaceBoundary
            For Each oCorridorSurfaceBoundary In oCorridorSurface.Boundaries
                Dim sBoundaryTitle As String
                If (oCorridorSurfaceBoundary.Type = aeccCorridorSurfaceInsideBoundary) Then
                    sBoundaryTitle = "  Inner Boundary: "
                Else
                    sBoundaryTitle = "  Outer Boundary: "
                End If
                oPara.Range.Text = sBoundaryTitle & oCorridorSurfaceBoundary.Name
                oPara.Range.InsertParagraphAfter
                vPoints = oCorridorSurfaceBoundary.GetPolygonPoints()
                oPara.Range.Text = "    " & UBound(vPoints) & " points"
                oPara.Range.InsertParagraphAfter

                ' To print out all point locations along the
                ' boundary, uncomment the following.  Doing so
                ' is not recommended because of the very large
                ' amount of information generated.

                'Dim i As Integer
                'For i = 0 To UBound(vPoints) '  & ", " &
                '    X = vPoints(i)(0)
                '    Y = vPoints(i)(1)
                '    Z = vPoints(i)(2)
                '    oPara.Range.Text = "    Point " & i & ": " & X & ", " & Y & ", " & Z
                '    oPara.Range.InsertParagraphAfter
                'Next i
                X = vPoints(1)(0)
                Y = vPoints(1)(1)
                Z = vPoints(1)(2)
                oPara.Range.Text = "    Point 1: " & X & ", " & Y & ", " & Z
                oPara.Range.InsertParagraphAfter

                ' Display information about each feature
                ' line component in this surface boundary.
                oPara.Range.Text = "  Feature line components"
                oPara.Range.InsertParagraphAfter
                oPara.Range.Text = "    Count: " & oCorridorSurfaceBoundary.FeatureLineComponents.Count
                oPara.Range.InsertParagraphAfter
                For Each oFeatureLineComponent In oCorridorSurfaceBoundary.FeatureLineComponents
                    oPara.Range.Text = "    Code: " & oFeatureLineComponent.FeatureLine.CodeName
                    oPara.Range.InsertParagraphAfter
                    oPara.Range.Text = "    Start station: " & oFeatureLineComponent.StartStation
                    oPara.Range.InsertParagraphAfter
                    oPara.Range.Text = "    End station: " & oFeatureLineComponent.EndStation
                    oPara.Range.InsertParagraphAfter
                    oPara.Range.Text = "    User Start station: " & CStr(oFeatureLineComponent.UseStartStation)
                    oPara.Range.InsertParagraphAfter
                    oPara.Range.Text = "    User End station: " & CStr(oFeatureLineComponent.UseEndStation)
                    oPara.Range.InsertParagraphAfter
                    oPara.Range.Text = ""
                    oPara.Range.InsertParagraphAfter
                Next ' Feature line components
            Next ' Corridor surface boundaries
            
            ' For each surface, display information about
            ' the surface's mask.
            Dim oCorridorSurfaceMask As AeccCorridorSurfaceMask
            For Each oCorridorSurfaceMask In oCorridorSurface.Masks
                oPara.Range.Text = "  Mask: " & oCorridorSurfaceMask.Name
                oPara.Range.InsertParagraphAfter
                vPoints = oCorridorSurfaceMask.GetPolygonPoints()
                oPara.Range.Text = "    " & UBound(vPoints) & " points"
                oPara.Range.InsertParagraphAfter

                ' To print out all point locations along the
                ' boundary, uncomment the following.  Doing so
                ' is not recommended because of the very large
                ' amount of information generated.

                'Dim i As Integer
                'For i = 0 To UBound(vPoints) '  & ", " &
                '    X = vPoints(i)(0)
                '    Y = vPoints(i)(1)
                '    Z = vPoints(i)(2)
                '    oPara.Range.Text = "    Point " & i & ": " & X & ", " & Y & ", " & Z
                '    oPara.Range.InsertParagraphAfter
                'Next i
                X = vPoints(1)(0)
                Y = vPoints(1)(1)
                Z = vPoints(1)(2)
                oPara.Range.Text = "    Point 1: " & X & ", " & Y & ", " & Z
                oPara.Range.InsertParagraphAfter

                ' Display information about each feature
                ' line component in this surface boundary.
                oPara.Range.Text = "  Feature line components"
                oPara.Range.InsertParagraphAfter
                oPara.Range.Text = "    Count: " & oCorridorSurfaceMask.FeatureLineComponents.Count
                oPara.Range.InsertParagraphAfter
                For Each oFeatureLineComponent In oCorridorSurfaceMask.FeatureLineComponents
                    oPara.Range.Text = "    Code: " & oFeatureLineComponent.FeatureLine.CodeName
                    oPara.Range.InsertParagraphAfter
                    oPara.Range.Text = "    Start station: " & oFeatureLineComponent.StartStation
                    oPara.Range.InsertParagraphAfter
                    oPara.Range.Text = "    End station: " & oFeatureLineComponent.EndStation
                    oPara.Range.InsertParagraphAfter
                    oPara.Range.Text = "    User Start station: " & oFeatureLineComponent.UseStartStation
                    oPara.Range.InsertParagraphAfter
                    oPara.Range.Text = "    User End station: " & oFeatureLineComponent.UseEndStation
                    oPara.Range.InsertParagraphAfter
                    oPara.Range.Text = ""
                    oPara.Range.InsertParagraphAfter
                Next ' Feature line components
            Next ' Corridor surface masks
        Next ' oCorridorSurface
        
    Next ' Corridors
    
    Close #1
    
    ' Function completed successfully.
    ListCorridorsToWord = True
End Function ' ListCorridorsToWord


'
'
'
Public Function DisplaySubassemblyInfoToWord(oAppliedSubassembly As AeccAppliedSubassembly)
    ' NOTE: BaselineHookedTo returns an object of type AeccBaseBaseline.
    ' But AeccBaseBaseline is not instansable - it is only an interface.
    ' That is, only the following line is possible: Dim oBaseBaseline As IAeccBaseBaseline
    ' Must use one of the types derived from the IAeccBaseBaseline interface,
    ' like AeccBaseline, AeccOffsetBaseline, or AeccHardcodedOffsetBaseline.
    ' Dim oBaseline as AeccBaseline
    ' Set oBaseline = oAppliedSubassembly.BaselineHookedTo ' not going to use it here - we are already dealing with this baseline.
    
    ' Get the SOE (Station to baseline, Offset to
    ' baseline, Elevation to baseline) of the specified
    ' subassembly.
    Dim S, O, E As Double
    With oAppliedSubassembly
        S = .OriginStationOffsetElevationToBaseline(0)
        O = .OriginStationOffsetElevationToBaseline(1)
        E = .OriginStationOffsetElevationToBaseline(2)
    End With
    oPara.Range.Text = "  Station to baseline  : " & S
    oPara.Range.InsertParagraphAfter
    oPara.Range.Text = "  Offset to baseline   : " & O
    oPara.Range.InsertParagraphAfter
    oPara.Range.Text = "  Elevation to baseline: " & E
    oPara.Range.InsertParagraphAfter
    
    ' Get information about the subassembly template
    ' from the database.
    Dim oSubassembly As AeccSubassembly
    Set oSubassembly = oAppliedSubassembly.SubassemblyDbEntity
    Dim sSubInfo As String
    sSubInfo = oSubassembly.Name
    oPara.Range.Text = "  Subassembly name: " & sSubInfo
    oPara.Range.InsertParagraphAfter
                                
    DisplaySubassemblyInfoToWord = True
End Function


'
' Create a volume surface from the intersection between
' the surfaces, and report the amount of fill and cut
' between the two.
'
' NOTE: This function is hard-coded to look for
' surfaces named "Corridor - (1) Datum"  and
' "Corridor - (1) Top" in the current document.
' This is the case with the file "Corridor-5b.dwg"
' which can be found in the "C:\Program Files\
' AutoCAD Civil 3D 2009\Help\Civil 3D Tutorials\Drawings
' Drawings" directory.
'
Public Function CreateVolumeSurface() As Boolean
    ' Get the collection of all surfaces in the drawing.
    Dim oSurfaces As AeccSurfaces
    Set oSurfaces = g_oRoadwayDocument.Surfaces

    ' Assign the setup information for the volume
    ' surface we will create.
    Dim oTinVolumeCreationData As New AeccTinVolumeCreationData
    oTinVolumeCreationData.Name = VOLUME_SURFACE_NAME
    oTinVolumeCreationData.BaseLayer = g_oRoadwayDocument.Layers.Item(0).Name
    oTinVolumeCreationData.Layer = g_oRoadwayDocument.Layers.Item(0).Name
    Set oTinVolumeCreationData.BaseSurface = oSurfaces.Item("EG")
    Set oTinVolumeCreationData.ComparisonSurface = oSurfaces.Item("Corridor - (1) Datum")
    oTinVolumeCreationData.Style = oSurfaces.Item("EG").StyleName
    oTinVolumeCreationData.Description = "Volume surface of corridor"
    
    ' Create a volume surface that represents the
    ' difference between the two surfaces.
    Dim oTinVolumeSurface As AeccTinVolumeSurface
    On Error Resume Next
    Set oTinVolumeSurface = oSurfaces.AddTinVolumeSurface(oTinVolumeCreationData)
    On Error GoTo 0
    If (oTinVolumeSurface Is Nothing) Then
        MsgBox "Corridor surfaces could not be found."
        CreateVolumeSurface = False
        Exit Function
    End If
    
    ' Get information about the volume surface and
    ' display it in a messagebox.
    Dim dNetVol As Double
    Dim dCutVol As Double
    Dim dFillVol As Double
    dNetVol = oTinVolumeSurface.Statistics.NetVolume
    dCutVol = oTinVolumeSurface.Statistics.CutVolume
    dFillVol = oTinVolumeSurface.Statistics.FillVolume
    MsgBox "Net Volume = " & dNetVol & " cu.m" & _
      vbNewLine & "Cut = " & dCutVol & " cu.m" & _
      vbNewLine & "Fill = " & dFillVol & " cu.m", _
      vbOKOnly, _
      "Differences between """ & _
      oTinVolumeCreationData.BaseSurface.Name & _
      """ and """ & _
      oTinVolumeCreationData.ComparisonSurface.Name & _
      """"
    
    CreateVolumeSurface = True
End Function ' CreateVolumeSurface


'
' Open a new instance of Word, and set the module
' variable "oPara" for use by other functions.
'
Public Function OpenWordInstance() As Boolean
    Dim oWordApp As Word.Application
    Dim oWordDoc As Word.Document

    ' Start Word and open the document template.
    On Error Resume Next
    Set oWordApp = GetObject(, "Word.Application")
    On Error GoTo 0
    If Err.Number <> 0 Then
        Err.Clear
        On Error Resume Next
        Set oWordApp = CreateObject("Word.Application")
        On Error GoTo 0
        If Err.Number <> 0 Then
            MsgBox "Could not start Microsoft Word."
            Err.Clear
            OpenWordInstance = False
            Exit Function
        End If
    End If
    oWordApp.Visible = True
    On Error Resume Next
    Set oWordDoc = oWordApp.Documents.Add
    On Error GoTo 0
    If oWordDoc Is Nothing Then
        MsgBox "Could not create a new Word document."
        OpenWordInstance = False
        Exit Function
    End If
    
    ' Create a reference to the object that lets you
    ' add new paragraphs to the current Word
    ' document for use throughout this module.
    Set oPara = oWordDoc.Content.Paragraphs.Add
    OpenWordInstance = True
End Function ' OpenWordInstance


'
' Create a new assembly style and a new roadway style
' set with one link style and one shape style.
'
Public Function CreateStyles() As Boolean
    ' Create a new assembly style and change it so that the
    ' place where the assembly attaches to the main baseline
    ' is marked with a red X.
    Dim oAssemblyStyle As AeccAssemblyStyle
    Set oAssemblyStyle = g_oRoadwayDocument.AssemblyStyles.Add(ASSEMBLY_STYLE_NAME)
    With oAssemblyStyle.MarkerStyleAtMainBaseline
        .CustomMarkerStyle = aeccCustomMarkerX
        .MarkerDisplayStylePlan.color = 10 ' red
        .MarkerDisplayStylePlan.Visible = True
    End With
    
    ' Create a new shape style that creates shapes with an
    ' orange border and a yellow hatch fill.
    Dim oShapeStyle As AeccRoadwayShapeStyle
    Set oShapeStyle = g_oRoadwayDocument.ShapeStyles.Add(SHAPE_STYLE_NAME)
    With oShapeStyle
        .AreaFillDisplayStylePlan.color = 50 ' yellow
        .AreaFillDisplayStylePlan.Visible = True
        .AreaFillHatchDisplayStylePlan.HatchType = aeccHatchPreDefined
        .AreaFillHatchDisplayStylePlan.Pattern = "LINE"
        .BorderDisplayStylePlan.color = 30 ' orange
        .BorderDisplayStylePlan.Visible = True
    End With
    
    ' Create a new link style that colors the link green.
    Dim oLinkStyle As AeccRoadwayLinkStyle
    Set oLinkStyle = g_oRoadwayDocument.LinkStyles.Add(LINK_STYLE_NAME)
    With oLinkStyle
        .LinkDisplayStylePlan.color = 80
        .LinkDisplayStylePlan.Visible = True
    End With
    
    ' Create a new style set using our previously created
    ' styles.
    Dim oStyleSet As AeccRoadwayStyleSet
    Set oStyleSet = g_oRoadwayDocument.StyleSets.Add(STYLE_SET_NAME)
    Call oStyleSet.Add( _
        aeccLinkType, _
        "TOP", _
        g_oRoadwayDocument.LinkStyles.Item(LINK_STYLE_NAME))
    Call oStyleSet.Add( _
        aeccShapeType, _
        "BASE", _
        g_oRoadwayDocument.ShapeStyles.Item(SHAPE_STYLE_NAME))
    
    ' Assign our new style set as the style set in current use.
    oStyleSet.InitAsCurrent
    
End Function

Attribute VB_Name = "Globals"
'
' MODULE_ID {Globals.bas}
' {CorridorSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


Global Const VOLUME_SURFACE_NAME As String = "Corridor Volume"
Global Const ALIGNMENT_NAME As String = "Alignment 01"
Global Const PROFILE_NAME As String = "Profile 01"
Global Const CORRIDOR_NAME As String = "Corridor 01"

Global Const ASSEMBLY_STYLE_NAME As String = "New Style 01"
Global Const SHAPE_STYLE_NAME As String = "Shape Style 01"
Global Const LINK_STYLE_NAME As String = "Link Style 01"
Global Const STYLE_SET_NAME As String = "Style Set 01"

Attribute VB_Name = "Subroutines"
'
' MODULE_ID {Subroutines.bas}
' {CorridorSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'

' This sample demonstrates how to access various types
' of information about corridors that exist in the
' current document.  It is hard-coded for use with the
' "Corridor-4b.dwg" file located in the Civil
' "Help\Civil 3D Tutorials\Drawings\" directory.  The
' sample will work for other corridors, except that
' the volume surface test will not create a volume
' surface.


'
' Main entry point from the VBARUN dialog box.
'


Sub CreateCorridorExample()
    'always get the objects again since MDI is supported
    If (GetBaseCivilObjects = False) Then
        Exit Sub
    End If
    
    ' Create a new corridor using an alignment, profile,
    ' and assembly.
    If (CreateCorridor() = False) Then
        Exit Sub
    End If
    
End Sub


Sub GetCorridorInformationExample()
    'always get the objects again since MDI is supported
    If (GetBaseCivilObjects = False) Then
        Exit Sub
    End If
    
    ' Demonstrate viewing and setting roadway-specific
    ' ambient settings.
    Call SetAmbientSettings
    
    ' Open an instance of Word for the display of
    ' information from all further functions.
    If (OpenWordInstance() = False) Then
        Exit Sub
    End If
    
    ' Display all assemblies in the current document.
    If (ListAssembliesToWord() = False) Then
        Exit Sub
    End If
    
    ' Display all corridors in the current document.
    If (ListCorridorsToWord() = False) Then
        Exit Sub
    End If
    
    ' Use surface methods to gain information about
    ' the corridor surfaces.
    Call CreateVolumeSurface
    
    g_oCivilApp.Update
End Sub
