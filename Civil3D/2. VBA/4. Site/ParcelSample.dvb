Attribute VB_Name = "BaseObjects"
'
' MODULE_ID {BaseObjects.bas}
' {ParcelSample.dvb}
'
' Copyright {2003-2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

Public g_vCivilApp As AeccApplication
Public g_oDocument As AeccDocument
Public g_oAeccDb As AeccDatabase

'
'
' Function to set up the global Civil 3D application, document
' and database objects that will be used by the program.
'
Function GetBaseCivilObjects() As Boolean
    Dim oApp As AcadApplication
    Set oApp = ThisDrawing.Application
    ' NOTE - Always specify the version number.
    Const sAppName = "AeccXUiLand.AeccApplication.10.0"
    Set g_vCivilApp = oApp.GetInterfaceObject(sAppName)
    If (g_vCivilApp Is Nothing) Then
        MsgBox "Error creating " & sAppName & "."
        GetBaseCivilObjects = False
        Exit Function
    End If
    Set g_oDocument = g_vCivilApp.ActiveDocument
    Set g_oAeccDb = g_oDocument.Database
    GetBaseCivilObjects = True
End Function

Attribute VB_Name = "Globals"
'
' MODULE_ID {Globals.bas}
' {ParcelSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


Global Const SITE_NAME As String = "Sample site"
Global Const SITE_STYLE_NAME As String = "Sample site style"

Attribute VB_Name = "Parcel"
'
' MODULE_ID {Parcel.bas}
' {ParcelSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
Option Explicit


'
' Create an AeccParcel object and display its properties.
'
Public Function CreateParcel() As Boolean
    Dim i, j, k, l As Integer
    Dim oParcelLoop As AeccParcelLoop
    Dim oParcels As AeccParcels

    ' Get the parent site for the parcels.
    Dim oSite As AeccSite
    Set oSite = g_oDocument.Sites.Item(SITE_NAME)
    If (oSite Is Nothing) Then
        Debug.Print "Error getting sample site."
        CreateParcel = False
        Exit Function
    End If
    
    Set oParcels = oSite.Parcels

    ' Add segments to the site.  The segments will automatically form
    ' parcels if they form a closed space.  The aeccParcelSegment
    ' return values from AddLine, AddCurve and AddEntity will not be
    ' used, so we won't bother collecting them.
    Dim oSegment As AeccParcelSegment

    ' Not for any parcel
    Call oSite.ParcelSegments.AddLine(50, 275, 150, 275)
    ' Parcel 1
    Set oSegment = oSite.ParcelSegments.AddLine(0, 0, 0, 200)
    Call oSite.ParcelSegments.AddCurve(0, 200, -0.5, 200, 200)
    Call oSite.ParcelSegments.AddLine(200, 200, 200, 0)
    Call oSite.ParcelSegments.AddLine(200, 0, 0, 0)
    ' Parcel 2, which shares a segment with parcel 1
    Call oSite.ParcelSegments.AddCurve2(200, 200, 330, 180, 400, 200)
    Call oSite.ParcelSegments.AddLine(400, 200, 400, 0)

    ' This will complete parcel 2, as well as form parcel 3.
    Dim oPolyline As AcadPolyline
    Dim dPoints(0 To 8) As Double
    dPoints(0) = 400: dPoints(1) = 0: dPoints(2) = 0
    dPoints(3) = 325: dPoints(4) = 25: dPoints(5) = 0
    dPoints(6) = 200: dPoints(7) = 0: dPoints(8) = 0
    Set oPolyline = g_oDocument.Database.ModelSpace.AddPolyline(dPoints)
    oPolyline.Closed = True
    ' Passing True as the second parameter will delete the
    ' polyline entity once the parcel segment has been created.
    Call oSite.ParcelSegments.AddFromEntity(oPolyline, True)

    g_vCivilApp.Update
    g_vCivilApp.ZoomExtents

    '
    ' Query and display all parcel info.
    '
    Dim oParcel As AeccParcel

    ' Go through all parcels.
    For i = 0 To oParcels.Count - 1
        Set oParcel = oParcels.Item(i)
        
        MsgBox "Parcel name: " & oParcel.Name & vbLf _
            & "        area: " & oParcel.Statistics.Area & vbLf _
            & "   perimeter: " & oParcel.Statistics.Perimeter
        Debug.Print "Parcel name: " & oParcel.Name
        Debug.Print "number of loops: " & CStr(oParcel.ParcelLoops.Count)
        ' Go through all parcel loops in this parcel.
        For j = 0 To oParcel.ParcelLoops.Count - 1
            Set oParcelLoop = oParcel.ParcelLoops.Item(j)
            Debug.Print "number of loop elements: " & CStr(oParcelLoop.Count)
            ' Go through all elements in this parcel loop.
            For k = 0 To oParcelLoop.Count - 1
                Dim oSegmentElement As AeccParcelSegmentElement
                Set oSegmentElement = oParcelLoop.Item(k)
                
                Debug.Print "   loop element " & CStr(k) & ": " & CStr(oParcelLoop.Item(k).StartX) & "," & CStr(oParcelLoop.Item(k).StartY) & " to " & CStr(oParcelLoop.Item(k).EndX) & ", " & CStr(oParcelLoop.Item(k).EndY)

                If (TypeOf oSegmentElement Is AeccParcelSegmentLine) Then
                    Dim oSegmentLine As AeccParcelSegmentLine
                    Set oSegmentLine = oSegmentElement
                    Debug.Print "      is a line. "
                ElseIf (TypeOf oSegmentElement Is AeccParcelSegmentCurve) Then
                    Dim oSegmentCurve As AeccParcelSegmentCurve
                    Set oSegmentCurve = oSegmentElement
                    Debug.Print "      is a curve with a bulge of:" & oSegmentCurve.Bulge & "  delta of:" & oSegmentCurve.Delta & "  radius of:" & oSegmentCurve.Radius & "  tangent of:" & oSegmentCurve.Tangent
                End If
            Next k
        Next j
    Next i

    ' Loop through all parcel segments to see how they
    ' compare.
    For i = 0 To oSite.ParcelSegments.Count - 1
        Debug.Print "Parcel Segment:" & i & "  count = " & oSite.ParcelSegments.Item(i).Count
        For j = 0 To oSite.ParcelSegments.Item(i).Count - 1
            Debug.Print "   " & oSite.ParcelSegments.Item(i).Item(j).StartX & "," & oSite.ParcelSegments.Item(i).Item(j).StartY & " to " & oSite.ParcelSegments.Item(i).Item(j).EndX & "," & oSite.ParcelSegments.Item(i).Item(j).EndY
        Next j
    Next i
    
    
    ' Set the last parcel's style properties.
    ' First, make a new style and store it in the document's collection of parcel styles.
    Dim oParcelStyle As AeccParcelStyle
    Dim oParcelStyles As AeccParcelStyles
    Set oParcelStyles = g_oDocument.ParcelStyles
    On Error Resume Next
    Set oParcelStyle = oParcelStyles.Item(SITE_STYLE_NAME)
    On Error GoTo 0
    ' If the "Sample Style" style does not exist, we will make it.
    If (oParcelStyle Is Nothing) Then
        Set oParcelStyle = oParcelStyles.Add(SITE_STYLE_NAME)
        oParcelStyle.ObservePatternFillDistance = True ' if this is true, it only hatches an thin area inside the lines
        oParcelStyle.PatternFillDistance = 20
        oParcelStyle.SegmentsDisplayStyle2d.color = 20 ' red-orange
        oParcelStyle.AreaFillDisplayStyle2d.color = 20
        oParcelStyle.AreaFillDisplayStyle2d.Visible = True
        oParcelStyle.AreaFillDisplayStyle2d.Lineweight = 20
        oParcelStyle.AreaFillHatchDisplayStyle2d.UseAngleOfObject = True
        oParcelStyle.AreaFillHatchDisplayStyle2d.ScaleFactor = 3.8
        oParcelStyle.AreaFillHatchDisplayStyle2d.Spacing = 1.5
        oParcelStyle.AreaFillHatchDisplayStyle2d.UOffset = 1.5
        oParcelStyle.AreaFillHatchDisplayStyle2d.VOffset = 1.5
        oParcelStyle.AreaFillHatchDisplayStyle2d.Pattern = "AR-SAND"
        oParcelStyle.AreaFillHatchDisplayStyle2d.HatchType = aeccHatchPreDefined
    End If

    ' Assign the "Sample Style" style to the first parcel.
    oSite.Parcels.Item(0).Style = oParcelStyle
    
    ' Make a default style for use with the segment display order
    ' functions.
    Set oParcelStyle = Nothing
    On Error Resume Next
    Set oParcelStyle = oParcelStyles.Item("Default")
    On Error GoTo 0
    ' If the "Default" style does not exist, we will make it.
    If (oParcelStyle Is Nothing) Then
        Set oParcelStyle = oParcelStyles.Add("Default")
        ' Do not change any style parameters from the default values.
    End If

    oParcel.Visible = True
    oParcel.Update
    
    CreateParcel = True
End Function ' CreateParcel

Attribute VB_Name = "Site"
'
' MODULE_ID {Site.bas}
' {ParcelSample.dvb}
'
' Copyright {2003-2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'
' Make sure that a site with the required name exists. If it does not,
' create a new AeccSite object.
'
Public Function CreateSite() As Boolean
    Dim oSites As AeccSites
    Set oSites = g_oDocument.Sites
    Dim oSite As AeccSite
    
    On Error Resume Next
    Set oSite = oSites.Item(SITE_NAME)
    On Error GoTo 0
    If (oSite Is Nothing) Then
        On Error Resume Next
        Set oSite = oSites.Add(SITE_NAME)
        On Error GoTo 0
        If (oSite Is Nothing) Then
            Debug.Print "Error creating Site."
            CreateSite = False
            Exit Function
        End If
    End If

    ' NextAutoCounterParcel sets the starting identification
    ' number for newly created parcels.  The first parcel
    ' created from parcel segments will be 300, the next 301,
    ' and so on.
    oSite.NextAutoCounterParcel = 300
    
    CreateSite = True
End Function

Attribute VB_Name = "Subroutines"
'
' MODULE_ID {Subroutines.bas}
' {ParcelSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
Option Explicit


'
' This sample demonstrates how to create a parcel by adding line,
' curve, and entity segments. After its creation, parcel properties
' are queried and shown in a dialog.
'
' Parcel object has a dependency of the site object so a site must
' be created first.
'
' Note: Global variables declared in Application module.
'
'
Sub CreateParcels()
    ' Always get the objects again since MDI is supported
    If (GetBaseCivilObjects() = False) Then
        Exit Sub
    End If
    
    If (CreateSite() = False) Then
        Debug.Print "Error creating a site."
        Exit Sub
    End If

    If (CreateParcel() = False) Then
        Debug.Print "Error creating a parcel."
        Exit Sub
    End If
    
    g_vCivilApp.Update
End Sub
