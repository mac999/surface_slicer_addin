Attribute VB_Name = "BaseObjects"
'
' MODULE_ID {BaseObjects.bas}
' {SurfacePointsSample.dvb}
'
' Copyright {2003-2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

Public g_oCivilApp As AeccApplication
Public g_oDocument As AeccDocument
Public g_oDatabase As AeccDatabase


'
' Start Civil 3D and create Civil 3D document and database objects.
'
Function GetGlobalCivilObjects() As Boolean
    Dim oAcadApp As AcadApplication
    Set oAcadApp = ThisDrawing.Application
    ' NOTE - Always specify the version number.
    Const sAppName = "AeccXUiLand.AeccApplication.10.0"
    Set g_oCivilApp = oAcadApp.GetInterfaceObject(sAppName)
    If (g_oCivilApp Is Nothing) Then
        MsgBox "Error creating " & sAppName & ", exit."
        GetGlobalCivilObjects = False
        Exit Function
    End If
    Set g_oDocument = g_oCivilApp.ActiveDocument
    Set g_oDatabase = g_oDocument.Database

    ' Mark that this function was already called.  No need
    ' do perform this action again once we already have the
    ' objects.
    GetGlobalCivilObjects = True
End Function

Attribute VB_Name = "Globals"
'
' MODULE_ID {Globals.bas}
' {SurfacePointsSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


Global Const POINT_STYLE_NAME As String = "Sample point style"
Global Const POINT_LABEL_STYLE_NAME As String = "Sample point label style"
Global Const POINT_DESCRIPTION_KEY_SET_NAME As String = "Sample key Set"
' Key names are short because they are used as parts of the
' AeccPoint.RawDescription string with many parameters, and
' a long name would be cumbersome.  No spaces are allowed.
Global Const POINT_DESCRIPTION_KEY_FORMAT As String = "SAMPLE"
Global Const POINT_DESCRIPTION_KEY_BASE As String = "SAMP"
Global Const POINT_DESCRIPTION_KEY_NAME As String = POINT_DESCRIPTION_KEY_BASE & "*"
' You can use the AeccPoint.RawDescription string property
' to tell Civil which description key to use for that point.
' You can also pass parameters to describe how the point is
' displayed.  In this case, we are passing a value which we
' will later use to scale the size of the point marker.
Global Const POINT_RAW_DESCRIPTION As String = POINT_DESCRIPTION_KEY_BASE & " 5"

Global Const SURFACE_STYLE_NAME As String = "Sample surface style"

Attribute VB_Name = "PointStyle"
'
' MODULE_ID {PointStyle.bas}
' {SurfacePointsSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create a new point style with the name given.  Returns
' false if the style could not be made.
'
Public Function CreatePointStyle(sStyleName As String) As Boolean
    Dim oPointStyle As AeccPointStyle
    Dim oPointStyles As AeccPointStyles
    Set oPointStyles = g_oDocument.PointStyles
    
    ' We will use the style if it already exists.  If
    ' it does not, we will add a new style.
    On Error Resume Next
    Set oPointStyle = oPointStyles.Item(sStyleName)
    ' Stop error checking as quickly as possible, or it might hide errors
    ' in your code.
    On Error GoTo 0
    If (oPointStyle Is Nothing) Then
        Set oPointStyle = oPointStyles.Add(sStyleName)
    End If

    ' This style will substitute the normal point marker
    ' with a dot with a circle around it.
    oPointStyle.MarkerType = aeccUseCustomMarker
    oPointStyle.CustomMarkerStyle = aeccCustomMarkerDot
    oPointStyle.CustomMarkerSuperimposeStyle = aeccCustomMarkerSuperimposeCircle

    CreatePointStyle = True
End Function


'
' Takes an existing and valid oLabelStyle and adds unique
' and visible (if not aesthetically pleasing) style
' elements to it so their effects can be clearly seen.
' Units below depend on ambient settings.
'
Public Function CreateLabelStyle(oLabelStyle As AeccLabelStyle) As Boolean
    Dim oLabelStyleTickComponent As AeccLabelStyleTickComponent
    Dim oLabelStyleBlockComponent As AeccLabelStyleBlockComponent
    Dim oLabelStyleLineComponent As AeccLabelStyleLineComponent
    Dim oLabelStyleTextComponent As AeccLabelStyleTextComponent

    ' Add to the AeccLabelStyle object an object for managing
    ' the style of label ticks.  This style governs the
    ' properties of the tick mark placed at regular intervals
    ' (in this case, at every station).
    On Error Resume Next
    oLabelStyle.TickComponents.Remove "New Tick"
    Set oLabelStyleTickComponent = oLabelStyle.TickComponents.Item("New Tick")
    On Error GoTo 0
    If (oLabelStyleTickComponent Is Nothing) Then
        Set oLabelStyleTickComponent = oLabelStyle.TickComponents.Add("New Tick")
    End If
    ' Specify what kind of symbol is used for the tick.
    'oLabelStyleTickComponent.BlockName = "AeccTickLine"
    oLabelStyleTickComponent.Lineweight.Value = 60 ' .60 mm
    oLabelStyleTickComponent.AlignWithObject = True ' perpendicular to alignment
    oLabelStyleTickComponent.Angle = 0# ' in radians
    oLabelStyleTickComponent.Visibility = True

    ' Add to the AeccLabelStyle object an object for managing
    ' the style of label blocks.  This style governs arbitrary
    ' symbols.  We will use this to add a circular tick mark
    ' around the current line tick mark.
    On Error Resume Next
    oLabelStyle.BlockComponents.Remove "New Block"
    Set oLabelStyleBlockComponent = oLabelStyle.BlockComponents.Item("New Block")
    On Error GoTo 0
    If (oLabelStyleBlockComponent Is Nothing) Then
        Set oLabelStyleBlockComponent = oLabelStyle.BlockComponents.Add("New Block")
    End If
    'oLabelStyleBlockComponent.BlockName = "AeccTickCircle"
    oLabelStyleBlockComponent.Visibility = True
    
    ' Add to the AeccLabelStyle object an object for managing
    ' the style of label lines.  This style governs lines placed
    ' at each station.  We will use this to point out which
    ' station each distantly located text label belongs to.
    On Error Resume Next
    oLabelStyle.LineComponents.Remove "New Line"
    Set oLabelStyleLineComponent = oLabelStyle.LineComponents.Item("New Line")
    On Error GoTo 0
    If (oLabelStyleLineComponent Is Nothing) Then
        Set oLabelStyleLineComponent = oLabelStyle.LineComponents.Add("New Line")
    End If
    oLabelStyleLineComponent.color = 40 ' orange-yellow
    oLabelStyleLineComponent.Angle = 0.7854 ' 2.094 ' radians, = 120 degrees
    oLabelStyleLineComponent.Length = 0.015
    oLabelStyleLineComponent.StartPointXOffset = 0.005
    oLabelStyleLineComponent.StartPointYOffset = 0.005
    oLabelStyleLineComponent.Visibility = True

    ' We will change what text is displayed, and move
    ' it under and to the side of each point.
    '
    ' Label objects have at least one text component
    ' automatically created.  We will just modify the
    ' alredy existing text component.
    Set oLabelStyleTextComponent = oLabelStyle.TextComponents.Item(0)
    ' Curve the text to follow the curves of the alignment.
    'oLabelStyleTextComponent.AllowToCurve = True
    oLabelStyleTextComponent.XOffset = -0.01
    oLabelStyleTextComponent.YOffset = 0.008
    oLabelStyleTextComponent.Contents = "N<[Point Number]>"
    oLabelStyleTextComponent.color = 253 ' light grey
    
    ' Everything is fine.  Return true.
    CreateLabelStyle = True
End Function

Attribute VB_Name = "Points"
'
' MODULE_ID {Points.bas}
' {SurfacePointsSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' Use Add point groups from the treeview UI to see
' the result of a point getting built into the surface.

Private g_oPointGroup As AeccPointGroup


' This function will enumerate through all existing points and
' list them in the debug window.  It will compute the average
' (mean) location and report it in a message box.
Public Function EnumExistingPoints() As Boolean
    Dim oPoints As AeccPoints
    Set oPoints = g_oDocument.Points
    
    ' Add points to the document's Points collection.
    Dim lCountAdded As Long
    Dim vLocations As Variant
    Const NUM_LOCATIONS As Long = 3
    Dim dLocations(0 To (3 * NUM_LOCATIONS) - 1) As Double ' 3 for each point location
    dLocations(0) = 4927: dLocations(1) = 3887: dLocations(2) = 150
    dLocations(3) = 5101: dLocations(4) = 3660: dLocations(5) = 250
    dLocations(6) = 5144: dLocations(7) = 3743: dLocations(8) = 350
    ' The AddMultiple method takes a variant parameter
    ' for the array.
    vLocations = dLocations
    lCountAdded = oPoints.AddMultiple(NUM_LOCATIONS, dLocations, 0)
    
    Dim i As Long
    Dim avgEasting As Double
    Dim avgNorthing As Double
    Dim avgElevation As Double

    Dim oPoint As AeccPoint
    For Each oPoint In oPoints
        avgEasting = avgEasting + oPoint.Easting
        avgNorthing = avgNorthing + oPoint.Northing
        avgElevation = avgElevation + oPoint.Elevation
    Next
    avgEasting = avgEasting / oPoints.Count
    avgNorthing = avgNorthing / oPoints.Count
    avgElevation = avgElevation / oPoints.Count
    MsgBox "Average easting: " & avgEasting & vbNewLine & "Average northing: " & avgNorthing & vbNewLine & "Average elevation: " & avgElevation & vbNewLine & "Number of points: " & oPoints.Count
    EnumExistingPoints = True
End Function ' enumExistingPoints



' Creates some points manually and adds them to the document.
' Creates a point group from those points and manipulates
' the points as a group.  Adds the point group points to
' an existing TIN surface.
'
Public Function CreatePoints() As Boolean
    Dim i As Integer
    
    Dim dLocation1(0 To 2) As Double
    Dim dLocation2(0 To 2) As Double
    Dim dLocation3(0 To 2) As Double
    dLocation1(0) = 4958: dLocation1(1) = 4078: dLocation1(2) = 400
    dLocation2(0) = 5507: dLocation2(1) = 3176: dLocation2(2) = 300
    dLocation3(0) = 4177: dLocation3(1) = 3539: dLocation3(2) = 200
    Dim oPoints As AeccPoints
    Set oPoints = g_oDocument.Points
    
    Dim oPoint1 As AeccPoint
    Dim oPoint2 As AeccPoint
    Dim oPoint3 As AeccPoint
    
    ' All points must have a unique name.
    ' We can avoid duplication by first checking to see if a point
    ' with the name we want exists.  If it does not exist, we create
    ' a new point with that name.  If it does, we can modify that
    ' point.
    Dim bFound As Boolean
    Dim lFoundAt As Long
    bFound = False
    ' Loop through all points and check against the name we want.
    For i = 0 To oPoints.Count - 1
        If (oPoints.Item(i).Name = "point1") Then
            bFound = True
            ' Points are only accessable by index.  Record the index
            ' to be used later.
            lFoundAt = i
        End If
    Next i

    If (bFound = True) Then
        Set oPoint1 = oPoints.Item(lFoundAt)
    Else
        Set oPoint1 = oPoints.Add(dLocation1)
        oPoint1.Name = "point1"
    End If

    ' Create point2 and add it to the list of all points in the
    ' document.  If the program was run before, you will likely
    ' get the "Duplicate Point Name" dialog box.
    Set oPoint2 = oPoints.Add(dLocation2)
    oPoint2.Name = "point2"
    
    ' Create point3 and add it to the list of all points in the
    ' document.  If the program was run before, you will likely
    ' get the "Duplicate Point Name" dialog box.
    Set oPoint3 = oPoints.Add(dLocation3)
    oPoint3.Name = "point3"
    
    '''''''''''''''''''''''''''''''''''''''''''''''''''''''''''
    ' Point Style
    
    ' Adjust the style of point1.  We will create a new style object
    ' and pass that to the point object.
    If (CreatePointStyle(POINT_STYLE_NAME) = False) Then
        CreatePoints = False
        Exit Function
    End If
    oPoint1.Style = g_oDocument.PointStyles.Item(POINT_STYLE_NAME)
    oPoint1.RawDescription = "Using: " & POINT_STYLE_NAME
    
    ' Adjust the style of point2.  We will use a predefined style
    ' that already exists in the document.
    oPoint2.Style = g_oDocument.PointStyles.Item(1) ' Use whatever the second style is.
    oPoint2.RawDescription = "Using: " & g_oDocument.PointStyles.Item(1).Name


    '''''''''''''''''''''''''''''''''''''''''''''''''''''''''''
    ' Point Label Style
        
    ' We will create a new label style object and pass that to
    ' the point object.
    Dim oLabelStyle As AeccLabelStyle

    ' Create a new point label style object for us to modify.
    On Error Resume Next
    g_oDocument.PointLabelStyles.Remove POINT_LABEL_STYLE_NAME
    Set oLabelStyle = g_oDocument.PointLabelStyles.Add(POINT_LABEL_STYLE_NAME)
    On Error GoTo 0
    If (oLabelStyle Is Nothing) Then
        On Error Resume Next
        Set oLabelStyle = g_oDocument.PointLabelStyles.Item(POINT_LABEL_STYLE_NAME)
        On Error GoTo 0
        If (oLabelStyle Is Nothing) Then
            CreatePoints = False
            Exit Function
        End If
    End If
    
    ' Call function to set up the label style we will use.
    Call CreateLabelStyle(oLabelStyle)
    oPoint1.LabelStyle = oLabelStyle
    
    
    '''''''''''''''''''''''''''''''''''''''''''''''''''''''''''
    ' Using Point Description Keys
    
    ' As was demonstrated, you can adjust the style and
    ' settings of points currently in the drawing.  However,
    ' points stored in text files do not have this information
    ' stored with them.  Point Description Keys were invented
    ' for this purpose.  By giving the points text descriptions
    ' that match a particular point description key name, you
    ' can give that point the styles and settings you need.
    
    Dim oImportOptions As New AeccPointImportOptions
    Dim sFileName As String
    Dim sFileFormat As String
    Dim iCount As Integer
    
    sFileName = g_oCivilApp.Path & "\Sample\Civil 3D API\COM\Vba\SurfacePoints\SampleDescriptivePointFile.txt"
    sFileFormat = "PENZD (comma delimited)"
    oImportOptions.PointDuplicateResolution = aeccPointDuplicateOverwrite
    iCount = oPoints.ImportPoints(sFileName, sFileFormat, oImportOptions)
    If (iCount = 0) Then
        MsgBox "Error: no points loaded from file (function: createPoints)."
        CreatePoints = False
        Exit Function
    End If
    
    g_oCivilApp.Update
    
    CreatePoints = True
End Function ' CreatePoints


'
' Create a point description key into a new point
' description key set.  The style and label style will
' come from the same methods that are used to make
' styles for the points in the createPoints function.
' Returns False if it was unable to perform this task.
'
Public Function CreatePointDescriptionKey() As Boolean
    ' This function should be called after createPoints,
    ' so the style should alredy exist in the documents
    ' collection of styles.  If the point style has not
    ' yet been made, make it.  If it cannot be made, exit
    ' the function reporting an error.
    Dim oPointStyle As AeccPointStyle
    On Error Resume Next
    Set oPointStyle = g_oDocument.PointStyles.Item(POINT_STYLE_NAME)
    On Error GoTo 0
    If (oPointStyle Is Nothing) Then
        If (CreatePointStyle(POINT_STYLE_NAME) = False) Then
            CreatePointDescriptionKey = False
            Exit Function
        End If
        Set oPointStyle = g_oDocument.PointStyles.Item(POINT_STYLE_NAME)
    End If
    
    ' Do the same thing for the point label style.
    Dim oLabelStyle As AeccLabelStyle
    On Error Resume Next
    Set oLabelStyle = g_oDocument.PointLabelStyles.Item(POINT_LABEL_STYLE_NAME)
    On Error GoTo 0
    If (oLabelStyle Is Nothing) Then
    ' Create a new point label style object for us to modify.
        On Error Resume Next
        Set oLabelStyle = g_oDocument.PointLabelStyles.Add(POINT_LABEL_STYLE_NAME)
        On Error GoTo 0
        If (oLabelStyle Is Nothing) Then
            CreatePointDescriptionKey = False
            Exit Function
        End If
        Call CreateLabelStyle(oLabelStyle)
    End If
    
    ' Make a new point description key set.
    Dim oPointDescriptionKeySet As AeccPointDescriptionKeySet
    On Error Resume Next
    ' Remove any old key set and make a new one.
    g_oDocument.PointDescriptionKeySets.Remove POINT_DESCRIPTION_KEY_SET_NAME
    Set oPointDescriptionKeySet = g_oDocument.PointDescriptionKeySets.Add(POINT_DESCRIPTION_KEY_SET_NAME)
    On Error GoTo 0
    If (oPointDescriptionKeySet Is Nothing) Then
        On Error Resume Next
        ' If the original set was in use, then it cannot be removed
        ' and a new one cannot be made.  In that case, use the one
        ' that is already there.
        Set oPointDescriptionKeySet = g_oDocument.PointDescriptionKeySets.Item(POINT_DESCRIPTION_KEY_SET_NAME)
        On Error GoTo 0
        If (oPointDescriptionKeySet Is Nothing) Then
            CreatePointDescriptionKey = False
            Exit Function
        End If
    End If

    ' Make a new point description key.
    Dim oPointDescriptionKey As AeccPointDescriptionKey
    On Error Resume Next
    ' Remove any old key and make a new one.
    oPointDescriptionKeySet.Remove POINT_DESCRIPTION_KEY_NAME
    Set oPointDescriptionKey = oPointDescriptionKeySet.Add(POINT_DESCRIPTION_KEY_NAME)
    On Error GoTo 0
    If (oPointDescriptionKey Is Nothing) Then
        On Error Resume Next
        ' If the original key was in use, then it cannot be removed
        ' and a new one cannot be made.  In that case, use the one
        ' that is already there.
        Set oPointDescriptionKey = oPointDescriptionKeySet.Item(POINT_DESCRIPTION_KEY_NAME)
        On Error GoTo 0
        If (oPointDescriptionKey Is Nothing) Then
            CreatePointDescriptionKey = False
            Exit Function
        End If
    End If
    
    
    oPointDescriptionKey.Format = POINT_DESCRIPTION_KEY_FORMAT
    oPointDescriptionKey.OverrideLayer = False
    
    ' We now have a key, and we now have styles to put
    ' into the key.
    oPointDescriptionKey.OverridePointLabelStyle = True
    oPointDescriptionKey.PointLabelStyle = oLabelStyle.Name
    oPointDescriptionKey.OverridePointStyle = True
    oPointDescriptionKey.PointStyle = oPointStyle.Name
    
    ' The key has other options that can be set as well.
    ' We will turn off the scale override, and instead
    ' scale to whatever is passed as the first parameter.
    oPointDescriptionKey.OverrideScaleParameter = True
    oPointDescriptionKey.OverrideFixedScaleFactor = False
    oPointDescriptionKey.UseDrawingScale = False
    oPointDescriptionKey.ScaleParameter = 1
    oPointDescriptionKey.ScaleXY = True
    
    ' And we will turn on the rotation override, and
    ' rotate all points using this key 45 degrees
    ' clockwise.
    oPointDescriptionKey.OverrideFixedRotation = True
    oPointDescriptionKey.FixedRotation = 0.785398163 ' radians
    oPointDescriptionKey.ClockwiseRotation = True
    
    CreatePointDescriptionKey = True
End Function ' CreatePointDescriptionKey


'
' Create a point group from the points currently in the
' document, demonstrating many different techniques for
' doing so.  It is assumed at least three points exist.
' The points in the point group will then be added to
' the first surface in the drawing if it is a TIN
' surface.
'
Public Function CreatePointGroup() As Boolean
    ' Make some point object for us to perform tests on.
    Dim oPoint1 As AeccPoint
    Dim oPoint2 As AeccPoint
    Dim oPoint3 As AeccPoint
    On Error Resume Next
    Set oPoint1 = g_oDocument.Points.Item(0)
    Set oPoint2 = g_oDocument.Points.Item(1)
    Set oPoint3 = g_oDocument.Points.Item(2)
    On Error GoTo 0
    If (oPoint3 Is Nothing) Then
        CreatePointGroup = False
        Exit Function
    End If

    ' Get the collection of all point groups from the document.
    Dim oPointGroups As AeccPointGroups
    Set oPointGroups = g_oDocument.PointGroups
    If (oPointGroups Is Nothing) Then
        CreatePointGroup = False
        Exit Function
    End If
    
    ' Get (or add if it does not exist) our group from the collection
    ' of groups.
    On Error Resume Next
    Set g_oPointGroup = oPointGroups.Item("Sample point group")
    On Error GoTo 0
    If (g_oPointGroup Is Nothing) Then
        Set g_oPointGroup = oPointGroups.Add("Sample point group")
    End If

    ' Add points to the point group using the QueryBuilder.
    g_oPointGroup.QueryBuilder.IncludeNames = "point1,point2"
    g_oPointGroup.QueryBuilder.IncludeNumbers = "3"
    ' You can also use wildcards.  The following example will
    ' select all points with a name beginning with "poi".
    ' g_oPointGroup.QueryBuilder.IncludeNames = "poi*"
    
    ' But do not select those points with an alitude above 300.
    'g_oPointGroup.QueryBuilder.ExcludeElevations = ">300"
    
    ' Check to see if the points exist in the group.
    If (g_oPointGroup.ContainsPoint(oPoint1.Number) = False) Then
        Debug.Print oPoint1.Name & " is NOT contained in the point group."
    Else
        Debug.Print oPoint1.Name & " is contained in the point group."
    End If
    If (g_oPointGroup.ContainsPoint(oPoint2.Number) = False) Then
        Debug.Print oPoint2.Name & " is NOT contained in the point group."
    Else
        Debug.Print oPoint2.Name & " is contained in the point group."
    End If
    If (g_oPointGroup.ContainsPoint(oPoint3.Number) = False) Then
        Debug.Print oPoint3.Name & " is NOT contained in the point group."
    Else
        Debug.Print oPoint3.Name & " is contained in the point group."
    End If
    
    ' Now that we have a point group, we can manipulate those points
    ' all in the same way.  For example, we can set the elevation of
    ' all the points in the group to 100.
    g_oPointGroup.Elevation = 100
    g_oPointGroup.OverrideElevation = True
    
    ' Add the point group to the surface.  The surface will
    ' automatically rebuild, incorporating the new points.
    On Error Resume Next
    Dim oSurf As AeccSurface
    Set oSurf = g_oDocument.Surfaces.Item(0)
    On Error GoTo 0
    If (oSurf Is Nothing) Then
        MsgBox "Error: no surface exists. Make sure you create a surface first."
        CreatePointGroup = False
        Exit Function
    End If
    
    If (oSurf.Type = aecckTinSurface) Then
        Dim oTinSurf As AeccTinSurface
        Set oTinSurf = oSurf
        oTinSurf.Update
        oTinSurf.PointGroups.Add g_oPointGroup
    Else
        CreatePointGroup = False
        Exit Function
    End If

    CreatePointGroup = True
End Function ' CreatePointGroup



' Loads a series of points from a text file and places them in
' the document.
Public Function LoadPointsFromText() As Boolean
    Dim oPoints As AeccPoints
    Dim oImportOptions As New AeccPointImportOptions
    Dim sFileName As String
    Dim sFileFormat As String
    Dim iCount As Integer
    
    Set oPoints = g_oDocument.Points
    sFileName = g_oCivilApp.Path & "\Sample\Civil 3D API\COM\Vba\SurfacePoints\Sample Point File.txt"
    sFileFormat = "PENZ (space delimited)"
    oImportOptions.PointDuplicateResolution = aeccPointDuplicateOverwrite
    iCount = oPoints.ImportPoints(sFileName, sFileFormat, oImportOptions)
    If (iCount = 0) Then
        MsgBox "Error: no points loaded from file (function loadPointsFromText)."
        LoadPointsFromText = False
        Exit Function
    End If

    ' Write them out again.
    Dim oExportOptions As New AeccPointExportOptions
    sFileName = g_oCivilApp.Path & "\Sample\Civil 3D API\COM\Vba\SurfacePoints\SamplePointFileOut.txt"
    oExportOptions.ExpandCoordinateData = True
    oPoints.ExportPoints sFileName, "PENZ (space delimited)", oExportOptions
    
    LoadPointsFromText = True
End Function

Attribute VB_Name = "Subroutines"
'
' MODULE_ID {Subroutines.bas}
' {SurfacePointsSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

''''''''''''''''''''''''''''''''''''''''''''''''''''''''''''
' This module contains all the exposed subroutines.



'
' This sample demonstrates how to import a LandXML file
' to create a TIN surface. Once the surface is created,
' three points and a point group is created. Using
' the point group query builder, some of the points are
' included in the point group. The point group is then
' added to the surface and the surface is rebuilt.  Other
' points are loaded from a file to demonstrate the Point
' Description Key.
'
Sub AddPointsToSurfaceTest()
    ' Always get the objects again since MDI is supported.
    If (GetGlobalCivilObjects() = False) Then
        MsgBox "Error accessing root objects."
        Exit Sub
    End If
    
    If (CreateSurfaceByImportXML() = False) Then
        MsgBox "Error importing an XML file to create a surface."
        Exit Sub
    End If
    
    If (CreatePointDescriptionKey() = False) Then
        Debug.Print "Error creating point description key."
        Exit Sub
    End If
    
    If (CreatePoints() = False) Then
        Debug.Print "Error creating points."
        Exit Sub
    End If
    
    If (CreatePointGroup() = False) Then
        Debug.Print "Error creating a point group."
        Exit Sub
    End If
End Sub


'
' Demonstrate loading points from a text file and writing
' them out again.
'
Sub LoadPointsFromFileTest()
    ' Always get the objects again since MDI is supported.
    If (GetGlobalCivilObjects() = False) Then
        Exit Sub
    End If
    
    If (LoadPointsFromText() = False) Then
        MsgBox "Error trying to load points from TXT file."
        Exit Sub
    End If
    Call EnumExistingPoints
End Sub


'
' Demonstrates creating a TIN surface and then loading
' points from a text file.
'
Sub CreateSurfaceFromFileTest()
    ' Always get the objects again since MDI is supported.
    If (GetGlobalCivilObjects() = False) Then
        Exit Sub
    End If
    
    If (CreateSurfaceByImportTXT() = False) Then
        MsgBox "Error trying to create surface from TXT file."
        Exit Sub
    End If

    Call EnumExistingSurfaces
End Sub


'
' Demonstrate the AeccDocument.SelectPoints method.
'
Sub SelectPointsWithMouseTest()
    ' Always get the objects again since MDI is supported.
    If (GetGlobalCivilObjects() = False) Then
        Exit Sub
    End If
    
    ' Tell the user what is going on.  Otherwise they
    ' might be confused.
    MsgBox "Create a selection box around any" & vbNewLine & "points.  Press Enter when done.", vbOKOnly, "SelectPoints Test"
    
    Dim vNumArray As Variant
    vNumArray = g_oDocument.SelectPoints
    
    Dim iCount As Integer
    iCount = (UBound(vNumArray) - LBound(vNumArray)) + 1
    MsgBox "You selected " & iCount & " points."
    
    ' Print all the point numbers selected to the debug window.
    Dim i As Integer
    For i = LBound(vNumArray) To UBound(vNumArray)
        Debug.Print vNumArray(i),
        ' You can do something to each point with the
        ' following code:
        '     Dim oPoint As AeccPoint
        '     Set oPoint = g_oDocument.Points.Item(i)
        ' Now you can act on the oPoint object.
    Next i
End Sub

Attribute VB_Name = "SurfaceStyle"
'
' MODULE_ID {SurfaceStyle.bas}
' {SurfacePointsSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create a new surface style with the given name.
'
Public Function CreateSurfaceStyle(sStyleName As String) As Boolean
    Dim oSurfaceStyle As AeccSurfaceStyle
    Dim oSurfaceStyles As AeccSurfaceStyles
    Set oSurfaceStyles = g_oDocument.SurfaceStyles
    
    ' We will use the style if it already exists.  If
    ' it does not, we will add a new style.
    On Error Resume Next
    Set oSurfaceStyle = oSurfaceStyles.Item(sStyleName)
    On Error GoTo 0
    If (oSurfaceStyle Is Nothing) Then
        Set oSurfaceStyle = oSurfaceStyles.Add(sStyleName)
    End If

    ' Make some style settings.
    oSurfaceStyle.ContourStyle.SmoothContours = True
    oSurfaceStyle.ContourStyle.SmoothingFactor = 10
    oSurfaceStyle.ContourStyle.SmoothingType = aeccAddVerticies
    oSurfaceStyle.ContourStyle.MinorContourDisplayStyle2d.Visible = True
    oSurfaceStyle.ContourStyle.MajorContourDisplayStyle3d.Visible = True
    oSurfaceStyle.ContourStyle.MinorContourDisplayStyle2d.Visible = True
    oSurfaceStyle.ContourStyle.MinorContourDisplayStyle3d.Visible = True
    oSurfaceStyle.ContourStyle.MinorContourInterval = 0.5
    oSurfaceStyle.ContourStyle.MajorContourColorScheme = "Greens"
    oSurfaceStyle.ContourStyle.MinorContourColorScheme = "Land"
    oSurfaceStyle.ContourStyle.UseColorScheme = True
    oSurfaceStyle.ContourStyle.MajorContourDisplayStyle2d.color = 43
    oSurfaceStyle.ContourStyle.MajorContourDisplayStyle3d.color = 43
    oSurfaceStyle.ContourStyle.MinorContourDisplayStyle2d.color = 47
    oSurfaceStyle.ContourStyle.MinorContourDisplayStyle3d.color = 47
    oSurfaceStyle.TriangleStyle.DisplayStyle2d.Visible = False
    oSurfaceStyle.TriangleStyle.DisplayStyle3d.Visible = False
    oSurfaceStyle.BoundaryStyle.DisplayStyle2d.Visible = True
    oSurfaceStyle.BoundaryStyle.DisplayStyle3d.Visible = True
    oSurfaceStyle.BoundaryStyle.DisplayStyle2d.color = 40
    oSurfaceStyle.BoundaryStyle.DisplayStyle3d.color = 40
    oSurfaceStyle.PointStyle.DisplayStyle2d.Visible = True
    oSurfaceStyle.PointStyle.DisplayStyle3d.Visible = True
    oSurfaceStyle.PointStyle.DisplayStyle2d.color = 20
    oSurfaceStyle.PointStyle.DisplayStyle3d.color = 20
    oSurfaceStyle.PointStyle.DataPointsDisplayType = 0 ' one pixel, no surround
    
    CreateSurfaceStyle = True
End Function


'
' Set display style to only display points along the exterior boundaries.
'
Public Function DisplayBorderPointsOnly() As Boolean
    Dim bRetVal As Boolean
    bRetVal = SetSurfaceDisplay(True, False, True, False, False, False, False, False, False, False, False, False)
    DisplayBorderPointsOnly = bRetVal
End Function

'
' Set display style to display TIN exterior boundaries and triangles in 2D and 3D
'
Public Function DisplayBorderTrianglesOnly() As Boolean
    Dim bRetVal As Boolean
    bRetVal = SetSurfaceDisplay(False, True, True, False, False, False, False, False, False, False, False, False)
    DisplayBorderTrianglesOnly = bRetVal
End Function

'
' Set display style to display only major and minor contours.
'
Public Function DisplayBorderMajorMinorContoursOnly() As Boolean
    Dim bRetVal As Boolean
    bRetVal = SetSurfaceDisplay(False, False, True, True, True, False, False, False, False, False, False, False)
    DisplayBorderMajorMinorContoursOnly = bRetVal
End Function

'
' Set display style to display only the border and grid of a grid surface.
'
Public Function DisplayBorderGridedOnly() As Boolean
    Dim bRetVal As Boolean
    bRetVal = SetSurfaceDisplay(False, False, True, False, False, False, True, False, False, False, False, False)
    DisplayBorderGridedOnly = bRetVal
End Function

'
' Set display style to display only the border and triangle slopes.
'
Public Function DisplayBorderSlopesOnly() As Boolean
    Dim bRetVal As Boolean
    bRetVal = SetSurfaceDisplay(False, False, True, False, False, False, False, False, False, True, False, False)
    DisplayBorderSlopesOnly = bRetVal
End Function

'
' Set display style to display only the border and slope indicators.
'
Public Function DisplayBorderSlopeArrowsOnly() As Boolean
    Dim bRetVal As Boolean
    bRetVal = SetSurfaceDisplay(False, False, True, False, False, False, False, False, False, False, True, False)
    DisplayBorderSlopeArrowsOnly = bRetVal
End Function

'
' Set display style to display only the border and watershed indicators.
'
Public Function DisplayBorderWatershedsOnly() As Boolean
    Dim bRetVal As Boolean
    bRetVal = SetSurfaceDisplay(False, False, True, False, False, False, False, False, False, False, False, True)
    DisplayBorderWatershedsOnly = bRetVal
End Function

'
' Set display style to display only the border.
'
Public Function DisplayBorderOnly() As Boolean
    Dim bRetVal As Boolean
    bRetVal = SetSurfaceDisplay(False, False, True, False, False, False, False, False, False, False, False, False)
    DisplayBorderOnly = bRetVal
End Function

'
' Set the surface display style according to the list
' of parameters.  The helper functions above make the
' application of common settings simple.
'
Public Function SetSurfaceDisplay(bPoints As Boolean, bTriangles As Boolean, bBorder As Boolean, _
    bMajorContour As Boolean, bMinorContour As Boolean, bUserContour As Boolean, _
    bGrided As Boolean, bDirections As Boolean, bElevations As Boolean, _
    bSlopes As Boolean, bSlopeArrows As Boolean, bWaterSheds As Boolean) As Boolean
    
    Dim oSurfaceStyle As AeccSurfaceStyle
    On Error Resume Next
    Set oSurfaceStyle = g_oDocument.SurfaceStyles.Item("Elevations")
    On Error GoTo 0
    If (oSurfaceStyle Is Nothing) Then
        On Error Resume Next
        Set oSurfaceStyle = g_oDocument.SurfaceStyles.Item("Standard")
        On Error GoTo 0
        If (oSurfaceStyle Is Nothing) Then
            Set oSurfaceStyle = g_oDocument.SurfaceStyles.Item(0)
        End If
    End If
    
    oSurfaceStyle.PointStyle.DisplayStyle2d.Visible = bPoints
    oSurfaceStyle.PointStyle.DisplayStyle3d.Visible = bPoints
    
    oSurfaceStyle.TriangleStyle.DisplayStyle2d.Visible = bTriangles
    oSurfaceStyle.TriangleStyle.DisplayStyle3d.Visible = bTriangles
    
    oSurfaceStyle.BoundaryStyle.DisplayExteriorBoundaries = bBorder
    oSurfaceStyle.BoundaryStyle.DisplayInteriorBoundaries = False
    
    oSurfaceStyle.BoundaryStyle.DisplayStyle2d.Visible = bBorder
    oSurfaceStyle.BoundaryStyle.DisplayStyle3d.Visible = bBorder
    
    oSurfaceStyle.ContourStyle.MajorContourDisplayStyle2d.Visible = bMajorContour
    oSurfaceStyle.ContourStyle.MajorContourDisplayStyle3d.Visible = bMajorContour
    
    oSurfaceStyle.ContourStyle.MinorContourDisplayStyle2d.Visible = bMinorContour
    oSurfaceStyle.ContourStyle.MinorContourDisplayStyle3d.Visible = bMinorContour
    
    oSurfaceStyle.ContourStyle.UserContourDisplayStyle2d.Visible = bUserContour
    oSurfaceStyle.ContourStyle.UserContourDisplayStyle3d.Visible = bUserContour
    
    oSurfaceStyle.GridStyle.DisplayStylePlan.Visible = bGrided
    oSurfaceStyle.GridStyle.DisplayStyleModel.Visible = bGrided
    
    oSurfaceStyle.DirectionStyle.DisplayStylePlan.Visible = bDirections
    oSurfaceStyle.DirectionStyle.DisplayStyleModel.Visible = bDirections
    
    oSurfaceStyle.ElevationStyle.DisplayStylePlan.Visible = bElevations
    oSurfaceStyle.ElevationStyle.DisplayStyleModel.Visible = bElevations
    
    oSurfaceStyle.SlopeStyle.DisplayStylePlan.Visible = bSlopes
    oSurfaceStyle.SlopeStyle.DisplayStyleModel.Visible = bSlopes
    
    oSurfaceStyle.SlopeArrowStyle.DisplayStylePlan.Visible = bSlopeArrows
    oSurfaceStyle.SlopeArrowStyle.DisplayStyleModel.Visible = bSlopeArrows
    
    oSurfaceStyle.WatershedStyle.DisplayStylePlan.Visible = bWaterSheds
    oSurfaceStyle.WatershedStyle.DisplayStyleModel.Visible = bWaterSheds
    
    ThisDrawing.Application.Update
    SetSurfaceDisplay = True
End Function

Attribute VB_Name = "Surfaces"
'
' MODULE_ID {Surfaces.bas}
' {SurfacePointsSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create a surface from the file EG.xml.
'
' NOTE: This uses a hard coded dirercory.
'
Public Function CreateSurfaceByImportXML() As Boolean
    Dim oSurfaces As AeccSurfaces
    Set oSurfaces = g_oDocument.Surfaces
    
    ' Get a reference to the existing surface ("EG").  If
    ' it does not exist, try loading surface data from a
    ' XML file.
    Dim oSurface As AeccSurface
    Dim sXmlFileName As String
    On Error Resume Next
    Set oSurface = oSurfaces.Item("EG")
    On Error GoTo 0
    
    If (oSurface Is Nothing) Then
        sXmlFileName = Application.Path & "\Sample\Civil 3D API\COM\Vba\SurfacePoints\EG.xml"
        Set oSurface = oSurfaces.ImportXML(sXmlFileName)
        If (oSurface Is Nothing) Then
            Debug.Print "Error loading XML file: " & Err.Description
            CreateSurfaceByImportXML = False
            Err.Clear
        End If
    End If
    
    ' Fill the screen with the surface, and show the triangles
    ' that make up the surface.
    ThisDrawing.Application.ZoomExtents
    Call DisplayBorderTrianglesOnly
    
    CreateSurfaceByImportXML = True
End Function


'
' Create a surface from the file SamplePointFile.
'
Public Function CreateSurfaceByImportTXT() As Boolean
    Dim oSurfaces As AeccSurfaces
    Set oSurfaces = g_oDocument.Surfaces
    
    ' Get a reference to the existing surface ("EG").  If
    ' it does not exist, make a new surface.
    Dim oSurface As AeccSurface
    Dim oTinSurface As AeccTinSurface
    On Error Resume Next
    Set oSurface = oSurfaces.Item("EG")
    On Error GoTo 0
    If (oSurface Is Nothing) Then
        Dim oTinCreationData As New AeccTinCreationData
        oTinCreationData.Name = "EG"
        oTinCreationData.Description = "TIN Surface from TXT file"
        oTinCreationData.Layer = g_oDocument.Layers.Item(0).Name
        oTinCreationData.BaseLayer = g_oDocument.Layers.Item(0).Name
        If (CreateSurfaceStyle(SURFACE_STYLE_NAME) = False) Then
            CreateSurfaceByImportTXT = False
            Exit Function
        End If
        oTinCreationData.Style = SURFACE_STYLE_NAME
        Set oTinSurface = oSurfaces.AddTinSurface(oTinCreationData)
    Else
        Set oTinSurface = oSurface
    End If
    
    
    ' Allow the user to input the location of the text file.
    ' We will use a hard coded default value.
    Dim sFileName As String
    ' sFileName = InputBox("Location of text file with point data", "Surface Sample", "C:\Program Files\Autodesk\AutoCAD Civil 3D 2011\Sample\Civil 3D API\COM\Vba\SurfacePoints\Sample Point File.txt")
    sFileName = g_oCivilApp.Path & "\Sample\Civil 3D API\COM\Vba\SurfacePoints\Sample Point File.txt"
    Dim sFileFormat As String
    sFileFormat = "PENZD (space delimited)"
    Dim oSurfacePointFile As AeccSurfacePointFile
    oSurfacePointFile = oTinSurface.PointFiles.Add(sFileName, sFileFormat, False, False, False)
    
    If Err.Number <> 0 Then
        MsgBox "Error importing a point file."
        CreateSurfaceByImportTXT = False
        Exit Function
    End If

    Debug.Print oTinSurface.PointGroups.Count
    Dim v As Variant
    v = oTinSurface.Points
    ' Print out all point coordinates.
    ' NOTE: The way points are stored (in a single array stored in
    ' the pattern xyzxyzxyz... instead of an array of 3 element
    ' arrays) is a change from Civil 3D 2007 to 2008.
    Debug.Print "Number of surface points: "; (UBound(oTinSurface.Points, 1) + 1) / 3
    Dim i As Integer
    For i = 0 To UBound(oTinSurface.Points) Step 3
        Debug.Print v(i), v(i + 1), v(i + 2)
    Next i

    ' Fill the screen with the surface, and show the
    ' contours of the surface.
    ThisDrawing.Application.ZoomExtents
    Call DisplayBorderMajorMinorContoursOnly
    
    CreateSurfaceByImportTXT = True
End Function
 

'
' Print a list of all surfaces in the current drawing
' to the debug window.
'
Public Function EnumExistingSurfaces() As Boolean
    Dim oSurface As AeccSurface
    Dim i As Integer
    
    For i = 0 To g_oDocument.Surfaces.Count - 1
        Set oSurface = g_oDocument.Surfaces.Item(i)
        Select Case (oSurface.Type)
            Case aecckGridSurface:
                Dim oGridSurface As AeccGridSurface
                Set oGridSurface = oSurface
                Debug.Print oGridSurface.Name & " is a Grid Surface with " & oGridSurface.Statistics.NumberOfPoints & " points."
            Case aecckTinSurface:
                Dim oTinSurface As AeccTinSurface
                Set oTinSurface = oSurface
                Debug.Print oTinSurface.Name & " is a TIN Surface with " & oTinSurface.Statistics.NumberOfTriangles & " triangles."
            Case aecckGridVolumeSurface:
                Dim oGridVolumeSurface As AeccGridVolumeSurface
                Set oGridVolumeSurface = oSurface
                Debug.Print oGridVolumeSurface.Name & " is a Grid Volume Surface with a net volume of " & oGridVolumeSurface.Statistics.NetVolume & "."
            Case aecckTinVolumeSurface:
                Dim oTinVolumeSurface As AeccTinVolumeSurface
                Set oTinVolumeSurface = oSurface
                Debug.Print oTinVolumeSurface.Name & " is a TIN Volume Surface with a net volume of " & oTinVolumeSurface.Statistics.NetVolume & "."
        End Select
    Next i
    
    EnumExistingSurfaces = True
End Function
