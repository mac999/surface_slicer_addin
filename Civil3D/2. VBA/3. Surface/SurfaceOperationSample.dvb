Attribute VB_Name = "BaseObjects"
'
' MODULE_ID {BaseObjects.bas}
' {SurfaceOperationSample.dvb}
'
' Copyright {2003-2008} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
Public g_oCivilApp As AeccApplication
Public g_oDocument As AeccDocument
Public g_oAeccDb As AeccDatabase


'
' Start Civil 3D and create Civil 3D document and database objects.
'
Public Function GetCivilObjects() As Boolean
    Dim oApp As AcadApplication
    Set oApp = ThisDrawing.Application
    ' NOTE - Always specify the version number.
    Const sAppName = "AeccXUiLand.AeccApplication.10.0"
    Set g_oCivilApp = oApp.GetInterfaceObject(sAppName)
    If g_oCivilApp Is Nothing Then
        MsgBox "Error creating " & sAppName & ", exit."
        GetCivilObjects = False
        Exit Function
    End If
    Set g_oDocument = g_oCivilApp.ActiveDocument
    Set g_oAeccDb = g_oDocument.Database
    GetCivilObjects = True
End Function

Attribute VB_Name = "Globals"
'
' MODULE_ID {Globals.bas}
' {SurfaceOperationSample.dvb}
'
' Copyright {2008} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' Set global constants for the names of our objects.

Global Const SURFACE_STYLE_NAME As String = "Surface style"
Global Const EXISTING_GROUND_NAME As String = "EG"
Global Const LOWER_GROUND_NAME As String = "LG"
Global Const UPPER_GROUND_NAME As String = "UG"
Global Const VOLUME_SURFACE_NAME As String = "VS"
Global Const POINT_GROUP_NAME As String = "Random Point Group"

Attribute VB_Name = "Subroutines"
'
' MODULE_ID {Subroutines.bas}
' {SurfaceOperationSample.dvb}
'
' Copyright {2008} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit



'
' These are all the subroutines that can be called from
' Civil 3D's VBRUN command.
'


'
' Create a random surface with breaklines, contours, and a boundary.
' Perform a watershed analysis on the surface, and output a report
' to an instance of Microsoft Word.
'
Sub PerformSurfaceWatershedExample()
    'always get the objects again since MDI is supported
    If (GetCivilObjects() = False) Then
        MsgBox "Error accessing top civil objects."
        Exit Sub
    End If
    
    ' Create a surface to perform a check on.
    Dim oTinSurface As AeccTinSurface
    Set oTinSurface = CreateRandomSurface()
    If (oTinSurface Is Nothing) Then
        MsgBox "Cannot create surface."
        Exit Sub
    End If
    
    ' Get the watershed information.
    If (GetSurfaceWatershedInfo(oTinSurface) = False) Then
        MsgBox "Cannot perform watershed analysis."
        Exit Sub
    End If
    
    ' Print some statistics of the surface.
    Debug.Print "triangles", "points"
    Debug.Print "---------", "------"
    Debug.Print oTinSurface.Statistics.NumberOfTriangles, oTinSurface.Statistics.NumberOfPoints
End Sub


'
' Create a random surface with breaklines, contours, and a boundary.
' Perform an elevation analysis on the surface, which will change
' colors of regions of the surface depending on the elevation
' range of the regions.
'
Public Sub PerformSurfaceElevationExample()
    If (GetCivilObjects() = False) Then
        MsgBox "Error accessing top civil objects."
        Exit Sub
    End If
    
    ' Create a surface to perform a check on.
    Dim oTinSurface As AeccTinSurface
    Set oTinSurface = CreateRandomSurface()
    If (oTinSurface Is Nothing) Then
        MsgBox "Cannot create surface."
        Exit Sub
    End If
    
    ' Create a surface elevation analysis.  This will
    ' change the color of regions of the surface depending
    ' on the elevation of those regions.
    Dim oSurfaceAnalysisElevation As AeccSurfaceAnalysisElevation
    Set oSurfaceAnalysisElevation = oTinSurface.SurfaceAnalysis.ElevationAnalysis
    Dim oElevationRegions As AeccElevationRegions
    ' NOTE: The number passed is not necessarily the same as the
    ' number of regions created.  We will keep recalculating the
    ' analysis until we get the right number of regions.
    Dim dRegions As Long
    Dim dAsk As Long
    Dim dCount As Long
    dRegions = 11 ' Number of regions I desire.
    dAsk = dRegions
    Do
        Set oElevationRegions = oSurfaceAnalysisElevation.CalculateElevationRegions(dAsk, False)
        Debug.Print oSurfaceAnalysisElevation.ElevationRegions.Count
        dAsk = dAsk + 1
    Loop Until oSurfaceAnalysisElevation.ElevationRegions.Count = dRegions
    
    ' Manually set the colors of the regions.  Lower elevations
    ' will be shades of green and higher elevations will be
    ' shades of gray, with higher elevations being brighter.
    oElevationRegions.Item(0).color = 255 ' white
    oElevationRegions.Item(1).color = 254
    oElevationRegions.Item(2).color = 253
    oElevationRegions.Item(3).color = 252
    oElevationRegions.Item(4).color = 251 ' very dark grey
    oElevationRegions.Item(5).color = 250 ' black
    oElevationRegions.Item(6).color = 90 ' bright green
    oElevationRegions.Item(7).color = 92
    oElevationRegions.Item(8).color = 94
    oElevationRegions.Item(9).color = 96
    oElevationRegions.Item(10).color = 98 ' very dark green

    ' Regions do not have to be contiguous.  This will create
    ' a slight gap between regions.
    oElevationRegions.Item(5).MaximumElevation = oElevationRegions.Item(5).MaximumElevation - 2.1
    oElevationRegions.Item(6).MinimumElevation = oElevationRegions.Item(6).MinimumElevation + 2.1
    ' Make sure that regions are visible.
    oTinSurface.Style.ElevationStyle.DisplayStyle2d.Visible = True
    ' oTinSurface.Style.ElevationStyle.DisplayStyle3d.Visible = True
End Sub

Attribute VB_Name = "Surface"
'
' MODULE_ID {Surface.bas}
' {SurfaceOperationSample.dvb}
'
' Copyright {2008} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit



'
' Creates a TIN surface manually from a series of points and
' add a number of features, such as boundaries and breaklines.
'
Public Function CreateRandomSurface() As AeccTinSurface
    ' If the initialization function cannot work, then
    ' we cannot load a surface.
    If (g_oDocument Is Nothing) Then
        Set CreateRandomSurface = Nothing
        Exit Function
    End If

    Dim oSurfaces As AeccSurfaces
    ' Get the collection of all surfaces in the drawing.
    Set oSurfaces = g_oDocument.Surfaces
    
    ' Delete any existing surface that may be around from
    ' previous runs of this program and go on to make a new
    ' surface.  If it still exists after we try to delete it,
    ' it probably means it is in use and cannot be deleted.
    ' In that case, do nothing.
    '
    ' We don't know what kind of surface it is yet, so we use
    ' a generic surface.
    Dim oSurface As AeccSurface
    Dim sDemFileName As String
    ' If we try to get an item that does not exist, we get an error.
    On Error Resume Next
    oSurfaces.Remove EXISTING_GROUND_NAME
    Set oSurface = oSurfaces.Item(EXISTING_GROUND_NAME)
    On Error GoTo 0
    If (oSurface Is Nothing) Then
        ' Create surface manually.
        Dim oTinSurface As AeccTinSurface
        Dim oTinCreationData As New AeccTinCreationData
        
        oTinCreationData.BaseLayer = g_oDocument.Layers.Item(0).Name
        oTinCreationData.Layer = g_oDocument.Layers.Item(0).Name
        oTinCreationData.Description = ""
        oTinCreationData.Name = EXISTING_GROUND_NAME
        oTinCreationData.Style = CreateSurfaceStyle(SURFACE_STYLE_NAME).Name
        Set oTinSurface = g_oDocument.Surfaces.AddTinSurface(oTinCreationData)
        If (oTinSurface Is Nothing) Then
            MsgBox "Error trying to create surface: " & Err.Description
            Set CreateRandomSurface = Nothing
            Exit Function
        End If

        ' Add random points to our surface.
        Call AddRandomPointsToSurface(oTinSurface, 50, 0#, 200#)

        ' For breakline and boundary functions.
        Dim o3DPoly As Acad3DPolyline
        Dim dPoints(0 To 11) As Double

        ' Add a breakpoint to the surface.
        ' First we need an AutoCAD entity (in this case a polyline)
        ' which serves to describe the boundary location.
        dPoints(0) = 1200: dPoints(1) = 1200: dPoints(2) = 300
        dPoints(3) = 2000: dPoints(4) = 3000: dPoints(5) = 300
        dPoints(6) = 3000: dPoints(7) = 2000: dPoints(8) = 300
        dPoints(9) = 3800: dPoints(10) = 3800: dPoints(11) = 300
        ' Add points to the document and let it create a polyline
        ' object.
        Set o3DPoly = Nothing
        Set o3DPoly = g_oDocument.Database.ModelSpace.Add3DPoly(dPoints)
        o3DPoly.Closed = False

        ' The mid-ordinate distance is the distance from the midway point of an arc
        ' to the chord of the arc. The mid-ordinate distance is used to add vertices
        ' to a polyline curve, creating an approximation of the curve using straight
        ' line segments. The length of these segments depends on the value of the
        ' mid-ordinate distance. (see User Manual page 728)
        Dim oBreakline As AeccSurfaceBreakline
        ' This has to be an array, even if we only have one entity.
        ' "Dim oPolyArray(0)" creates an array of one item.
        Dim oEntityArray(0) As AcadEntity
        Set oEntityArray(0) = o3DPoly
        Set oBreakline = oTinSurface.Breaklines.AddStandardBreakline(oEntityArray, "Sample Standard Break", 1#)

        ' Do it again, but this time we are making a wall breakline.
        dPoints(0) = 2700: dPoints(1) = 1200: dPoints(2) = 300
        dPoints(3) = 3500: dPoints(4) = 1500: dPoints(5) = 300
        dPoints(6) = 3750: dPoints(7) = 1800: dPoints(8) = 300
        dPoints(9) = 3900: dPoints(10) = 3000: dPoints(11) = 300
        Set o3DPoly = Nothing
        Set o3DPoly = g_oDocument.Database.ModelSpace.Add3DPoly(dPoints)
        o3DPoly.Closed = False
        ' This is an array of arrays of elevations, one array of
        ' elevations per entity.
        Dim vElevations(0) As Variant
        ' These are the elevations of the wall at each endpoint in
        ' the polyline entity.
        Dim dElevations(3) As Double
        ' This is an array of booleans, one for each entity.
        Dim bOffsets(0) As Boolean
        
        dElevations(0) = 30#: dElevations(1) = 90#: dElevations(2) = 90#: dElevations(3) = 40#
        vElevations(0) = dElevations
        bOffsets(0) = True
        
        Set oBreakline = Nothing
        Set oEntityArray(0) = Nothing
        Set oEntityArray(0) = o3DPoly
        
        Set oBreakline = oTinSurface.Breaklines.AddWallBreakline(oEntityArray, "Sample Wall Break", 1#, vElevations, bOffsets)
        
        Call AddTinSurfaceContour(oTinSurface)
        
        
        ' Manually add a boundary to the surface.  We must do this
        ' last because if we modify the surface (by, say, adding
        ' points or breaklines) then we might get triangles that
        ' cross the boundary line.
        ' First we need an AutoCAD entity (in this case a polyline)
        ' which serves to describe the boundary location.
        ' Define the 2D polyline points
        Dim oPoly As AcadPolyline
        dPoints(0) = 1000: dPoints(1) = 1000: dPoints(2) = 0
        dPoints(3) = 1000: dPoints(4) = 4000: dPoints(5) = 0
        dPoints(6) = 4000: dPoints(7) = 4000: dPoints(8) = 0
        dPoints(9) = 4000: dPoints(10) = 1000: dPoints(11) = 0
        ' Add points to the document and let it create a polyline
        ' object.
        Set oPoly = g_oDocument.Database.ModelSpace.AddPolyline(dPoints)
        oPoly.Closed = True

        ' The mid-ordinate distance is the distance from the midway point of an arc
        ' to the chord of the arc. The mid-ordinate distance is used to add vertices
        ' to a polyline curve, creating an approximation of the curve using straight
        ' line segments. The length of these segments depends on the value of the
        ' mid-ordinate distance. (see User Manual page 728)
        Dim oNewBoundary As AeccSurfaceBoundary
        Set oNewBoundary = oTinSurface.Boundaries.Add(oPoly, "Sample Boundary", aeccBoundaryOuter, True, 10#)


        ' Update all the changes we made to the drawing.
        g_oCivilApp.Update

        ' Zoom to see the entire surface.
        ThisDrawing.Application.ZoomExtents
        ' Return a reference to the surface object.
        Set CreateRandomSurface = oTinSurface
    Else
        ' There is already a surface.  Return a reference
        ' to it.
        Set CreateRandomSurface = oSurface
    End If

End Function ' CreateRandomSurface


'
'
'
'
Public Function CreateSurfaceStyle(sStyleName As String) As AeccSurfaceStyle
    ' Change the surface style so we see point information and all
    ' triangles in the surfaces.
    Dim oSurfaceStyle As AeccSurfaceStyle
    On Error Resume Next
    Set oSurfaceStyle = g_oDocument.SurfaceStyles.Item(sStyleName)
    On Error GoTo 0
    If oSurfaceStyle Is Nothing Then
        Set oSurfaceStyle = g_oDocument.SurfaceStyles.Add(sStyleName)
    End If
    ' Be sure to set all visibility properties because
    ' you cannot predict how the new or existing style
    ' might be set.
    oSurfaceStyle.PointStyle.DisplayStyle2d.Visible = True
    oSurfaceStyle.PointStyle.DisplayStyle3d.Visible = True
    oSurfaceStyle.TriangleStyle.DisplayStyle2d.Visible = True
    oSurfaceStyle.TriangleStyle.DisplayStyle3d.Visible = True
    oSurfaceStyle.BoundaryStyle.DisplayExteriorBoundaries = True
    oSurfaceStyle.BoundaryStyle.DisplayStyle2d.Visible = True
    oSurfaceStyle.BoundaryStyle.DisplayStyle3d.Visible = True
    oSurfaceStyle.ElevationStyle.DisplayStyle2d.Visible = False
    ' oSurfaceStyle.ElevationStyle.DisplayStyle3d.Visible = False
    oSurfaceStyle.ContourStyle.MajorContourDisplayStyle2d.Visible = False
    oSurfaceStyle.ContourStyle.MajorContourDisplayStyle3d.Visible = False
    oSurfaceStyle.ContourStyle.MinorContourDisplayStyle2d.Visible = False
    oSurfaceStyle.ContourStyle.MinorContourDisplayStyle3d.Visible = False
    oSurfaceStyle.ContourStyle.UserContourDisplayStyle2d.Visible = False
    oSurfaceStyle.ContourStyle.UserContourDisplayStyle3d.Visible = False
    oSurfaceStyle.GridStyle.DisplayStyle2d.Visible = False
    ' oSurfaceStyle.GridStyle.DisplayStyle3d.Visible = False
    oSurfaceStyle.DirectionStyle.DisplayStyle2d.Visible = False
    ' oSurfaceStyle.DirectionStyle.DisplayStyle3d.Visible = False
    oSurfaceStyle.SlopeStyle.DisplayStyle2d.Visible = False
    ' oSurfaceStyle.SlopeStyle.DisplayStyle3d.Visible = False
    oSurfaceStyle.SlopeArrowStyle.DisplayStyle2d.Visible = True
    ' oSurfaceStyle.SlopeArrowStyle.DisplayStyle3d.Visible = True
    oSurfaceStyle.WatershedStyle.DisplayStyle2d.Visible = False
    ' oSurfaceStyle.WatershedStyle.DisplayStyle3d.Visible = False

    ' Return a reference to the style.
    Set CreateSurfaceStyle = oSurfaceStyle
End Function


'
'
'
'
Public Function AddTinSurfaceContour(oTinSurface As AeccTinSurface) As Boolean
    ' Add a contour to the map.
    Dim dContourPoints(0 To 8) As Double
    Dim o3DPoly As Acad3DPolyline

    dContourPoints(0) = 2500: dContourPoints(1) = 1500: dContourPoints(2) = 100
    dContourPoints(3) = 2600: dContourPoints(4) = 1600: dContourPoints(5) = 100
    ' It does not matter that we specify a Z value of 50. It
    ' will still be located at an altitude of 100, just like
    ' the first point.
    dContourPoints(6) = 2400: dContourPoints(7) = 1600: dContourPoints(8) = 50
    Set o3DPoly = g_oDocument.Database.ModelSpace.Add3DPoly(dContourPoints)
    o3DPoly.Closed = True
    Dim oEntities(0) As AcadEntity
    Set oEntities(0) = o3DPoly
    'g_oDocument.Database.ModelSpace.Delete
    Dim oNewContour As AeccSurfaceContour
    Set oNewContour = oTinSurface.Contours.Add(oEntities, "Sample Contour", 55#, 0.0698, 63#, 1#) ' 0.0698 rad = 4 deg
End Function


'
' Calculate watershed information for the surface and display
' full information about each watershed region into an instance
' of Microsoft Word.
'
Public Function GetSurfaceWatershedInfo(oTinSurface As AeccTinSurface) As Boolean
    Dim i As Integer
    
    ' If MergeAdjacentBoundaries = True, then any watershed regions
    ' along the boundary that have boundary points or boundary
    ' segments that touch are joined into a single watershed.
    oTinSurface.SurfaceAnalysis.WatershedAnalysis.MergeAdjacentBoundaries = True
    ' If a depression has a minimum average depth smaller than this
    ' value, then water from the depression will drain into other
    ' watershed regions.
    oTinSurface.SurfaceAnalysis.WatershedAnalysis.MergeDepression = 10.65
    ' Calculate watershed regions.
    oTinSurface.SurfaceAnalysis.WatershedAnalysis.CalculateWatersheds
    ' Put watershed information into a Word document.
    Call ExportWatershedInfoToWord(oTinSurface.SurfaceAnalysis.WatershedAnalysis.WatershedRegions)
    
    GetSurfaceWatershedInfo = True
End Function


'
' Loop through all watershed regions of a watershed analysis
' and display information about all the draining points and
' segments into an instance of Microsoft Word.
'
Public Function ExportWatershedInfoToWord(oWSAnalysis As AeccWatershedRegions) As Boolean
    Dim oWordApp As Word.Application
    Dim oWordDoc As Word.Document
    Dim oPara As Word.Paragraph
    Dim i As Integer
    Dim j As Integer
    Dim k As Integer
    Dim sTargets As String
    Dim lTargets() As Long
    Dim varDrainsInto As Variant
    Dim vDrainPoint As Variant
    Dim vDrainSegments As Variant


    ' Start Word and open the document template.
    On Error Resume Next
    Set oWordApp = GetObject(, "Word.Application")
    On Error GoTo 0
    If Err.Number <> 0 Then
        Err.Clear
        On Error Resume Next
        Set oWordApp = CreateObject("Word.Application")
        On Error GoTo 0
        If Err.Number <> 0 Then
            MsgBox "Could not start Microsoft Word."
            Err.Clear
            ExportWatershedInfoToWord = False
            Exit Function
        End If
    End If
    If IsObjectValid(oWordApp) = False Then
        MsgBox "Microsoft Word needs to be running before you start this example."
    End If
    
    oWordApp.Visible = True
    On Error Resume Next
    Set oWordDoc = oWordApp.Documents.Add
    On Error GoTo 0
    If oWordDoc Is Nothing Then
        MsgBox "Could not create a new Word document."
        ExportWatershedInfoToWord = False
        Exit Function
    End If

    ' Insert a paragraph at the beginning of the document.
    Set oPara = oWordDoc.Content.Paragraphs.Add
    oPara.Range.Text = "Watershed Report"
    oPara.Range.Font.Bold = True
    oPara.Range.Font.Size = 18
    oPara.Format.SpaceAfter = 24    ' 24 pt spacing after paragraph.
    oPara.Range.InsertParagraphAfter
    
    ' Insert informational paragraph.
    ' "\endofdoc" is a predefined bookmark in Word.
    Set oPara = oWordDoc.Content.Paragraphs.Add(oWordDoc.Bookmarks("\endofdoc").Range)
    oPara.Range.Text = "There are " & CStr(oWSAnalysis.Count) & " watershed regions in the surface."
    oPara.Range.Font.Bold = False
    oPara.Range.Font.Size = 11
    oPara.Format.SpaceAfter = 24
    oPara.Range.InsertParagraphAfter
    
    
    ' For each of the watershed regions, we will find out what kind
    ' of region it actually is.  Then we will print a report of that
    ' region to Word.
    For i = 0 To oWSAnalysis.Count - 1
        Select Case (oWSAnalysis.Item(i).Type)
            Case aeccWatershedBoundaryPoint
                Dim oWSBoundaryPoint As AeccWatershedRegionBoundaryPoint
                Set oWSBoundaryPoint = oWSAnalysis.Item(i)
                vDrainPoint = oWSBoundaryPoint.BoundaryDrainPoint
                ' vDrainPoint is a variant array.  It has a length of 3 and
                ' is a xyz location of the drain.
                
                'Insert informational paragraphs.
                Set oPara = oWordDoc.Content.Paragraphs.Add(oWordDoc.Bookmarks("\endofdoc").Range)
                oPara.Range.Text = CStr(i) & ".  Region " & CStr(oWSAnalysis.Item(i).Id) & " (Drains into point on boundary).  Area: " & Format(oWSAnalysis.Item(i).Area, "#####.00")
                oPara.Range.Font.Bold = False
                oPara.Range.Font.Size = 11
                oPara.Format.SpaceAfter = 2
                oPara.Range.InsertParagraphAfter
                Set oPara = oWordDoc.Content.Paragraphs.Add(oWordDoc.Bookmarks("\endofdoc").Range)
                oPara.Range.Text = "This region drains to point: " & Format(vDrainPoint(0), "#####.00") & ", " & Format(vDrainPoint(1), "#####.00") & ", " & Format(vDrainPoint(2), "#####.00")
                oPara.Range.Font.Bold = False
                oPara.Range.Font.Size = 11
                oPara.Format.SpaceAfter = 16
                oPara.Range.InsertParagraphAfter
            Case aeccWatershedBoundarySegment
                Dim oWSBoundarySegment As AeccWatershedRegionBoundarySegment
                Set oWSBoundarySegment = oWSAnalysis.Item(i)
                ' NOTE: DrainSegments has been changed for the Civil 3D 2008.
                vDrainSegments = oWSBoundarySegment.BoundaryDrainSegment
                
                'Insert informational paragraphs.
                Set oPara = oWordDoc.Content.Paragraphs.Add(oWordDoc.Bookmarks("\endofdoc").Range)
                oPara.Range.Text = CStr(i) & ".  Region " & CStr(oWSAnalysis.Item(i).Id) & " (Drains into segment on boundary).  Area: " & Format(oWSAnalysis.Item(i).Area, "#####.00")
                oPara.Range.Font.Bold = False
                oPara.Range.Font.Size = 11
                oPara.Format.SpaceAfter = 2
                oPara.Range.InsertParagraphAfter
                
                Set oPara = oWordDoc.Content.Paragraphs.Add(oWordDoc.Bookmarks("\endofdoc").Range)
                oPara.Range.Text = "This region drains to the following " & (UBound(vDrainSegments) + 1) / 3 & " segments: "
                oPara.Range.Font.Bold = False
                oPara.Range.Font.Size = 11
                oPara.Format.SpaceAfter = 2
                oPara.Range.InsertParagraphAfter

                ' Information is held in a two-dimensional array.  The first
                ' dimension is each point in the polyline that makes up the
                ' series of segments, and the second hold the x, y, z coordinates
                ' of each point.
                ' This loops through all line segments and prints their end points.
                ' We use "UBound(vDrainSegments) - 3 Step 3" because the coordinates
                ' of the points are held in 3 contiguous values in a single array.
                For j = 0 To UBound(vDrainSegments) - 3 Step 3
                    Set oPara = oWordDoc.Content.Paragraphs.Add(oWordDoc.Bookmarks("\endofdoc").Range)
                    
                    oPara.Range.Text = Format(vDrainSegments(j + 0), "#####.00") & ", " & Format(vDrainSegments(j + 1), "#####.00") & ", " & Format(vDrainSegments(j + 2), "#####.00") & "  to  " & Format(vDrainSegments(j + 3), "#####.00") & ", " & Format(vDrainSegments(j + 4), "#####.00") & ", " & Format(vDrainSegments(j + 5), "#####.00")
                    oPara.Range.Font.Bold = False
                    oPara.Range.Font.Size = 11
                    ' Insert a larger gap between text lines after the last line.
                    ' "-5" because the last line of text will display a segment
                    ' of 2 points which are 6 elements of the vDrainSegments
                    ' array.  So we add the extra space when we are 6 values from
                    ' the end of the array.  Not including the element currently
                    ' referenced by "j" makes 5.
                    If (j = UBound(vDrainSegments) - 5) Then
                        oPara.Format.SpaceAfter = 16
                    Else
                        oPara.Format.SpaceAfter = 2
                    End If
                    oPara.Range.InsertParagraphAfter
                Next j
            Case aeccWatershedDepression
                Dim oWSDepression As AeccWatershedRegionDepression
                Set oWSDepression = oWSAnalysis.Item(i)
                Dim oDrains As AeccWatershedDrains
                Set oDrains = oWSDepression.Drains
                ' oDrains is a collection of drain objects that have a location and targets and nothing else.
                ' Target is a long array that I think are region IDs.
                
                ' Insert informational paragraphs.
                Set oPara = oWordDoc.Content.Paragraphs.Add(oWordDoc.Bookmarks("\endofdoc").Range)
                oPara.Range.Text = CStr(i) & ".  Region " & CStr(oWSAnalysis.Item(i).Id) & " (Depression).  Area: " & Format(oWSAnalysis.Item(i).Area, "#####.00")
                oPara.Range.Font.Bold = False
                oPara.Range.Font.Size = 11
                oPara.Format.SpaceAfter = 2
                oPara.Range.InsertParagraphAfter
                For j = 0 To oDrains.Count - 1
                    Set oPara = oWordDoc.Content.Paragraphs.Add(oWordDoc.Bookmarks("\endofdoc").Range)
                    oPara.Range.Font.Bold = False
                    oPara.Range.Font.Size = 11
                    
                    ' See what kind of drain targets we have.
                    If (UBound(oDrains.Item(j).Targets) = -1) Then
                        ' Print report saying this depression drains outside the surface.
                        oPara.Range.Text = "Drain through point " & CStr(j) & ": " & Format(oDrains.Item(j).Location(0), "#####.00") & ", " & Format(oDrains.Item(j).Location(1), "#####.00") & ", " & Format(oDrains.Item(j).Location(2), "#####.00") & " to the surface boundary."
                        ' Insert a larger gap between text lines after the last line.
                        If (j = oDrains.Count - 1) Then
                            oPara.Format.SpaceAfter = 16
                        Else
                            oPara.Format.SpaceAfter = 2
                        End If
                        oPara.Range.InsertParagraphAfter
                    Else
                        ' Print report for a drain into another region.
                        lTargets = oDrains.Item(j).Targets
                        sTargets = CStr(lTargets(0))
                        For k = 1 To UBound(lTargets)
                            sTargets = sTargets & ", " & CStr(lTargets(k))
                        Next k
                        
                        oPara.Range.Text = "Drain through point " & CStr(j) & ": " & Format(oDrains.Item(j).Location(0), "#####.00") & ", " & Format(oDrains.Item(j).Location(1), "#####.00") & ", " & Format(oDrains.Item(j).Location(2), "#####.00") & " and into the following regions: " & sTargets
                        ' Insert a larger gap between text lines after the last line.
                        If (j = oDrains.Count - 1) Then
                            oPara.Format.SpaceAfter = 16
                        Else
                            oPara.Format.SpaceAfter = 2
                        End If
                        oPara.Range.InsertParagraphAfter
                    End If
                Next j


                ' Use the following code to get the boundary for
                ' this depression.
                'Dim vBound As Variant
                'vBound = oWSDepression.BoundaryLine
                'For j = LBound(oWSDepression.BoundaryLine) To UBound(oWSDepression.BoundaryLine)
                '    Debug.Print vBound(j, 0), vBound(j, 1), vBound(j, 2)
                'Next j

           Case aeccWatershedFlat
                Dim oWSFlat As AeccWatershedRegionFlat
                Set oWSFlat = oWSAnalysis.Item(i)
                varDrainsInto = oWSFlat.DrainsInto
                ' varDrainsInto is an array of variants, each one of which is a
                ' long integer which containing region IDs.
                ' sTargets = CStr(varDrainsInto(0))
                sTargets = ""
                For k = 0 To UBound(varDrainsInto)
                    sTargets = sTargets & ", " & CStr(varDrainsInto(k))
                Next k

                'Insert informational paragraphs.
                Set oPara = oWordDoc.Content.Paragraphs.Add(oWordDoc.Bookmarks("\endofdoc").Range)
                oPara.Range.Text = CStr(i) & ".  Region " & CStr(oWSAnalysis.Item(i).Id) & " (Flat).  Area: " & Format(oWSAnalysis.Item(i).Area, "#####.00")
                oPara.Range.Font.Bold = False
                oPara.Range.Font.Size = 11
                oPara.Format.SpaceAfter = 2
                oPara.Range.InsertParagraphAfter
                Set oPara = oWordDoc.Content.Paragraphs.Add(oWordDoc.Bookmarks("\endofdoc").Range)
                oPara.Range.Text = "This region drains into the following regions: " & sTargets
                oPara.Range.Font.Bold = False
                oPara.Range.Font.Size = 11
                oPara.Format.SpaceAfter = 16
                oPara.Range.InsertParagraphAfter
            Case aeccWatershedMultiDrain
                Dim oWSMulti As AeccWatershedRegionMultiRegionDrain
                Set oWSMulti = oWSAnalysis.Item(i)
                ' vDrainPoint is a single point, like BoundaryPoint
                vDrainPoint = oWSMulti.DrainPoint
                ' varDrainsInto is an array of variants, each a region ID.
                varDrainsInto = oWSMulti.DrainsInto
                sTargets = CStr(varDrainsInto(0))
                For k = 1 To UBound(varDrainsInto)
                    sTargets = sTargets & ", " & CStr(varDrainsInto(k))
                Next k
                
                'Insert informational paragraphs.
                Set oPara = oWordDoc.Content.Paragraphs.Add(oWordDoc.Bookmarks("\endofdoc").Range)
                oPara.Range.Text = CStr(i) & ".  Region " & CStr(oWSAnalysis.Item(i).Id) & " (Drain through point into other regions).  Area: " & Format(oWSAnalysis.Item(i).Area, "#####.00")
                oPara.Range.Font.Bold = False
                oPara.Range.Font.Size = 11
                oPara.Format.SpaceAfter = 2
                oPara.Range.InsertParagraphAfter
                Set oPara = oWordDoc.Content.Paragraphs.Add(oWordDoc.Bookmarks("\endofdoc").Range)
                oPara.Range.Text = "This region drains to point: " & Format(vDrainPoint(0), "#####.00") & ", " & Format(vDrainPoint(1), "#####.00") & ", " & Format(vDrainPoint(2), "#####.00") & " and into the following regions: " & sTargets
                oPara.Range.Font.Bold = False
                oPara.Range.Font.Size = 11
                oPara.Format.SpaceAfter = 16
                oPara.Range.InsertParagraphAfter
            Case aeccWatershedMultiDrainNotch
                Dim oWSNotch As AeccWatershedRegionMultiRegionDrainNotch
                Set oWSNotch = oWSAnalysis.Item(i)
                ' NOTE: oWSNotch.DrainSegment has been changed for
                ' Civil 3D 2008.
                ' vDrainSegments is an array of all coordinates that make up
                ' the segments that this region drains into.  The elements
                ' that make up each segment endpoint are held in the array
                ' contiguously, in the form x,y,z,x,y,z,x,y,z...
                vDrainSegments = oWSNotch.DrainSegment
                ' varDrainsInto is an array of region IDs.
                varDrainsInto = oWSNotch.DrainsInto
                sTargets = CStr(varDrainsInto(0))
                For k = 1 To UBound(varDrainsInto)
                    sTargets = sTargets & ", " & CStr(varDrainsInto(k))
                Next k

                'Insert informational paragraphs.
                Set oPara = oWordDoc.Content.Paragraphs.Add(oWordDoc.Bookmarks("\endofdoc").Range)
                oPara.Range.Text = CStr(i) & ".  Region " & CStr(oWSAnalysis.Item(i).Id) & " (Drains through segments into other regions).  Area: " & Format(oWSAnalysis.Item(i).Area, "#####.00")
                oPara.Range.Font.Bold = False
                oPara.Range.Font.Size = 11
                oPara.Format.SpaceAfter = 2
                oPara.Range.InsertParagraphAfter
                
                ' Display each line segment this region drains through.
                Set oPara = oWordDoc.Content.Paragraphs.Add(oWordDoc.Bookmarks("\endofdoc").Range)
                oPara.Range.Text = "This region drains through these segments: "
                oPara.Range.Font.Bold = False
                oPara.Range.Font.Size = 11
                oPara.Format.SpaceAfter = 2
                oPara.Range.InsertParagraphAfter

                For j = 0 To UBound(vDrainSegments) - 3 Step 3
                    Set oPara = oWordDoc.Content.Paragraphs.Add(oWordDoc.Bookmarks("\endofdoc").Range)
                    oPara.Range.Text = Format(vDrainSegments(j + 0), "#####.00") & ", " & Format(vDrainSegments(j + 1), "#####.00") & ", " & Format(vDrainSegments(j + 2), "#####.00") & "  to  " & Format(vDrainSegments(j + 3), "#####.00") & ", " & Format(vDrainSegments(j + 4), "#####.00") & ", " & Format(vDrainSegments(j + 5), "#####.00")
                    oPara.Range.Font.Bold = False
                    oPara.Range.Font.Size = 11
                    oPara.Format.SpaceAfter = 2
                    oPara.Range.InsertParagraphAfter
                Next j
                
                ' Display each region this drains into.
                Set oPara = oWordDoc.Content.Paragraphs.Add(oWordDoc.Bookmarks("\endofdoc").Range)
                oPara.Range.Text = "and into the following regions: " & sTargets
                oPara.Range.Font.Bold = False
                oPara.Range.Font.Size = 11
                oPara.Format.SpaceAfter = 16
                oPara.Range.InsertParagraphAfter
            Case Else 'aeccWatershedUnknownSink
                Set oPara = oWordDoc.Content.Paragraphs.Add(oWordDoc.Bookmarks("\endofdoc").Range)
                oPara.Range.Text = CStr(i) & ".  Region " & CStr(oWSAnalysis.Item(i).Id) & " (Unknown region).  Area: " & Format(oWSAnalysis.Item(i).Area, "#####.00")
                oPara.Range.Font.Bold = False
                oPara.Range.Font.Size = 11
                oPara.Format.SpaceAfter = 16
                oPara.Range.InsertParagraphAfter
           End Select
    Next i

End Function ' ExportWatershedInfoToWord


'
' Create the specified number of random points and add them
' to the surface.  The points will be in within the range
' 0-5000 in both the X and Y dimensions.
'
Private Function AddRandomPointsToSurface(oTinSurface As AeccTinSurface, NumPoints As Integer, MinAlt As Double, MaxAlt As Double)
    Const MAX_X As Double = 5000
    Const MAX_Y As Double = 5000

    ' Make some random points and add them to the document's
    ' Points collection.
    Dim i As Integer
    Dim oPoints As AeccPoints
    Set oPoints = g_oDocument.points
    Dim dDifference As Double
    dDifference = MaxAlt - MinAlt
    For i = 0 To NumPoints - 1
        Dim pt(0 To 2) As Double
        pt(0) = Int(MAX_X * Rnd())
        pt(1) = Int(MAX_Y * Rnd())
        pt(2) = Int(dDifference * Rnd()) + MinAlt
        Dim oPoint As AeccPoint
        Set oPoint = oPoints.Add(pt)
        ' Differentiate the names based on the surface they belong to.
        oPoint.Name = oTinSurface.Name & "Point" & CStr(i)
    Next i

    ' Get the document's collection of Point Groups.
    Dim oPtGroups As AeccPointGroups
    Dim oPtGroup As AeccPointGroup
    Set oPtGroups = g_oDocument.PointGroups
    If (oPtGroups Is Nothing) Then
        AddRandomPointsToSurface = False
        Exit Function
    End If

    ' Make (or if it already exists, get) the point group for
    ' our random points.
    On Error Resume Next ' if we try to get an item that does not exist, we get an error.
    Set oPtGroup = oPtGroups.Item(POINT_GROUP_NAME & oTinSurface.Name)
    On Error GoTo 0
    If (oPtGroup Is Nothing) Then
        Set oPtGroup = oPtGroups.Add(POINT_GROUP_NAME & oTinSurface.Name)
    End If

    ' Add our random points to the Point Group.
    oPtGroup.QueryBuilder.IncludeNames = oTinSurface.Name & "Point" & "*"
    
    ' Check to see if things are working alright.
    If (oPtGroup.PointCount = 0) Then
        MsgBox "No points in point group"
        AddRandomPointsToSurface = False
        Exit Function
    End If

    ' Add the group of points to the TIN surface.  The surface is
    ' now made up of the random points.  It will automatically
    ' triangulate the points for us.
    oTinSurface.PointGroups.Add oPtGroup
    oTinSurface.Update

    AddRandomPointsToSurface = True
End Function ' AddRandomPointsToSurface
