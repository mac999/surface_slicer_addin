Attribute VB_Name = "Alignment"
'
' MODULE_ID {Alignment.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit



'
' Create a simple allignment using layout methods.
'
Public Function CreateAlignmentByLayout(oAlignment As AeccAlignment) As Boolean
    ' Get the site that the alignment will be part of,
    ' and the collection of the site's alignments.
    Dim oSite As AeccSite
    Dim oAlignments As AeccAlignments
    Set oSite = GetSite()
    If (oSite Is Nothing) Then
        CreateAlignmentByLayout = False
        Exit Function
    End If
    Set oAlignments = oSite.Alignments

    ' Create the alignment only if it has not already been created.
    On Error Resume Next
    Set oAlignment = oAlignments.Item(ALIGNMENT_NAME)
    On Error GoTo 0
    If (oAlignment Is Nothing) Then
        ' Set the style for the alignment.
        Dim oAlignmentStyle As AeccAlignmentStyle
        If (CreateAlignmentStyle(STYLE_NAME) = False) Then
            CreateAlignmentByLayout = False
            Exit Function
        End If
        Set oAlignmentStyle = g_oDocument.AlignmentStyles.Item(STYLE_NAME)
    
        ' Set the label style for the alignment.
        Dim oLabelStyleSet As AeccAlignmentLabelStyleSet
        If (CreateAlignmentLabelStyleSet(LABEL_STYLE_SET_NAME) = False) Then
            CreateAlignmentByLayout = False
            Exit Function
        End If
        Set oLabelStyleSet = g_oDocument.AlignmentLabelStyleSets.Item(LABEL_STYLE_SET_NAME)
        
        ' Add a blank alignment with our style sets to the
        ' collection of alignments.
        Set oAlignment = oAlignments.Add(ALIGNMENT_NAME, "0", oAlignmentStyle.Name, oLabelStyleSet.Name)
        If (oAlignment Is Nothing) Then
            Debug.Print "Error creating alignment: " & Err.Description & " - " & Err.Number
            Err.Clear
            ThisDrawing.Application.ZoomExtents
            CreateAlignmentByLayout = False
            Exit Function
        End If
    
        ' Add layout entities to the currently empty alignment.
        ' The alignment will consist of a tangent and a curve.
        Dim dPoint1(0 To 2) As Double
        Dim dPoint2(0 To 2) As Double
        Dim dRadius As Double
        Dim dLength As Double
        dPoint1(0) = 3932.4: dPoint1(1) = 3384.2: dPoint1(2) = 0
        dPoint2(0) = 4600.2: dPoint2(1) = 4150.9: dPoint2(2) = 0
        dRadius = 751.8
        dLength = 899.9
        
        Dim oAlignmentArc As AeccAlignmentArc
        Set oAlignmentArc = oAlignment.Entities.AddFixedCurve6(dPoint1, dPoint2, 751.8, True)
        Dim oAlignmentTangent As AeccAlignmentTangent
        Set oAlignmentTangent = oAlignment.Entities.AddFloatingLine2(oAlignmentArc.Id, dLength)
    
        ' Add some superelevation settings to the alignment.
        ' This is deprecated as of C3D2011
        
        ' Dim oSuperElevationData As AeccSuperElevationData
        ' Dim oSuperElevationElem As AeccSuperElevationDataElem
    
        ' Create a element at station 0+00.0.
        'Set oSuperElevationData = oAlignment.SuperelevationData
        'oSuperElevationData.Add 0, oSuperElevationElem
        
        ' Specify the new percent grade for each road segment.
        'oSuperElevationElem.SegmentCrossSlope(aeccSuperLeftOutShoulderCrossSlope) = 0#
        'oSuperElevationElem.SegmentCrossSlope(aeccSuperLeftOutLaneCrossSlope) = 0#
        'oSuperElevationElem.SegmentCrossSlope(aeccSuperLeftInLaneCrossSlope) = 0#
        'oSuperElevationElem.SegmentCrossSlope(aeccSuperLeftInShoulderCrossSlope) = 0#
        'oSuperElevationElem.SegmentCrossSlope(aeccSuperRightInShoulderCrossSlope) = 0#
        'oSuperElevationElem.SegmentCrossSlope(aeccSuperRightInLaneCrossSlope) = 0#
        'oSuperElevationElem.SegmentCrossSlope(aeccSuperRightOutLaneCrossSlope) = 0#
        'oSuperElevationElem.SegmentCrossSlope(aeccSuperRightOutShoulderCrossSlope) = 0#
        'oSuperElevationElem.TransPointType = aeccSuperManual
        'oSuperElevationElem.TransPointDesc = "Manual adjustment 1"
        'oSuperElevationElem.RawStation = 0
        
        ' Do the same for station 11+00.0.
        'oSuperElevationData.Add 1100, oSuperElevationElem
        'oSuperElevationElem.SegmentCrossSlope(aeccSuperLeftOutShoulderCrossSlope) = 0.05
        'oSuperElevationElem.SegmentCrossSlope(aeccSuperLeftOutLaneCrossSlope) = 0.02
        'oSuperElevationElem.SegmentCrossSlope(aeccSuperLeftInLaneCrossSlope) = 0.01
        'oSuperElevationElem.SegmentCrossSlope(aeccSuperLeftInShoulderCrossSlope) = 0.03
        'oSuperElevationElem.SegmentCrossSlope(aeccSuperRightInShoulderCrossSlope) = 0.03
        'oSuperElevationElem.SegmentCrossSlope(aeccSuperRightInLaneCrossSlope) = 0.01
        'oSuperElevationElem.SegmentCrossSlope(aeccSuperRightOutLaneCrossSlope) = 0.02
        'oSuperElevationElem.SegmentCrossSlope(aeccSuperRightOutShoulderCrossSlope) = 0.05
        'oSuperElevationElem.TransPointType = aeccSuperManual
        'oSuperElevationElem.TransPointDesc = "Manual adjustment 2"
        'oSuperElevationElem.RawStation = 1100
        
        ' Do the same for station 12+00.0.
        'oSuperElevationData.Add 1200, oSuperElevationElem
        'oSuperElevationElem.SegmentCrossSlope(aeccSuperLeftOutShoulderCrossSlope) = -0.03
        'oSuperElevationElem.SegmentCrossSlope(aeccSuperLeftOutLaneCrossSlope) = -0.02
        'oSuperElevationElem.SegmentCrossSlope(aeccSuperLeftInLaneCrossSlope) = -0.02
        'oSuperElevationElem.SegmentCrossSlope(aeccSuperLeftInShoulderCrossSlope) = -0.03
        'oSuperElevationElem.SegmentCrossSlope(aeccSuperRightInShoulderCrossSlope) = 0.03
        'oSuperElevationElem.SegmentCrossSlope(aeccSuperRightInLaneCrossSlope) = 0.02
        'oSuperElevationElem.SegmentCrossSlope(aeccSuperRightOutLaneCrossSlope) = 0.02
        'oSuperElevationElem.SegmentCrossSlope(aeccSuperRightOutShoulderCrossSlope) = 0.03
        'oSuperElevationElem.TransPointType = aeccSuperManual
        'oSuperElevationElem.TransPointDesc = "Manual adjustment 3"
        'oSuperElevationElem.RawStation = 1200

        ' Do the same for the end station.
        'oSuperElevationData.Add oAlignment.EndingStation, oSuperElevationElem
        'oSuperElevationElem.SegmentCrossSlope(aeccSuperLeftOutShoulderCrossSlope) = -0.03
        'oSuperElevationElem.SegmentCrossSlope(aeccSuperLeftOutLaneCrossSlope) = -0.02
        'oSuperElevationElem.SegmentCrossSlope(aeccSuperLeftInLaneCrossSlope) = -0.02
        'oSuperElevationElem.SegmentCrossSlope(aeccSuperLeftInShoulderCrossSlope) = -0.03
        'oSuperElevationElem.SegmentCrossSlope(aeccSuperRightInShoulderCrossSlope) = 0.03
        'oSuperElevationElem.SegmentCrossSlope(aeccSuperRightInLaneCrossSlope) = 0.02
        'oSuperElevationElem.SegmentCrossSlope(aeccSuperRightOutLaneCrossSlope) = 0.02
        'oSuperElevationElem.SegmentCrossSlope(aeccSuperRightOutShoulderCrossSlope) = 0.03
        'oSuperElevationElem.TransPointType = aeccSuperManual
        'oSuperElevationElem.TransPointDesc = "Manual adjustment 4"
        'oSuperElevationElem.RawStation = oAlignment.EndingStation

    End If

    CreateAlignmentByLayout = True
End Function

Attribute VB_Name = "AlignmentStyle"
'
' MODULE_ID {AlignmentStyle.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create an alignment style.  Make it simple because
' the focus is on the profile we will create along
' the alignment.
'
Function CreateAlignmentStyle(sStyleName As String) As Boolean
    Dim oAlignmentStyles As AeccAlignmentStyles
    Dim oAlignmentStyle As AeccAlignmentStyle
    
    ' Get the drawing's collection of alignment styles.
    On Error Resume Next
    Set oAlignmentStyles = g_oDocument.AlignmentStyles
    On Error GoTo 0
    If (oAlignmentStyles Is Nothing) Then
        Debug.Print "Error accessing collection of alignment styles: " & vbNewLine & Err.Description
        CreateAlignmentStyle = False
        Exit Function
    End If
    
    ' Get a particular style from the collection of styles.
    On Error Resume Next
    Set oAlignmentStyle = oAlignmentStyles.Item(sStyleName)
    On Error GoTo 0
    ' If the style does not exist, make a new one with that
    ' name.
    If (oAlignmentStyle Is Nothing) Then
        On Error Resume Next
        Set oAlignmentStyle = oAlignmentStyles.Add(sStyleName)
        On Error GoTo 0
        If (oAlignmentStyles Is Nothing) Then
            Debug.Print "Error trying to make a new alignment style: " & vbNewLine & Err.Description
            CreateAlignmentStyle = False
            Exit Function
        End If
    End If

    oAlignmentStyle.CurveDisplayStylePlan.color = 255 ' white
    oAlignmentStyle.CurveDisplayStylePlan.Visible = True
    oAlignmentStyle.LineDisplayStylePlan.color = 255 ' white
    oAlignmentStyle.LineDisplayStylePlan.Visible = True
    oAlignmentStyle.SpiralDisplayStylePlan.color = 255 ' white
    oAlignmentStyle.SpiralDisplayStylePlan.Visible = True
    oAlignmentStyle.ArrowDisplayStylePlan.Visible = True
    
    oAlignmentStyle.CurveExtensionsDisplayStylePlan.Visible = False
    oAlignmentStyle.LineExtensionsDisplayStylePlan.Visible = False
    
    g_oCivilApp.Update
    CreateAlignmentStyle = True
End Function


'
' Make an alignment label style set.  We just
' need the object to create the alignment - we
' will not actually be using labels on the
' alignment.
'
Function CreateAlignmentLabelStyleSet(sStyleSetName As String) As Boolean
    Dim oLabelStyleSet As AeccAlignmentLabelStyleSet
    
    On Error Resume Next
    Set oLabelStyleSet = g_oDocument.AlignmentLabelStyleSets.Item(sStyleSetName)
    On Error GoTo 0
    If (oLabelStyleSet Is Nothing) Then
        On Error Resume Next
        Set oLabelStyleSet = g_oDocument.AlignmentLabelStyleSets.Add(sStyleSetName)
        On Error GoTo 0
        If (oLabelStyleSet Is Nothing) Then
            CreateAlignmentLabelStyleSet = False
            Exit Function
        End If
    End If

    CreateAlignmentLabelStyleSet = True
End Function

Attribute VB_Name = "BaseObjects"
'
' MODULE_ID {BaseObjects.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
Public g_oCivilApp As AeccApplication
Public g_oDocument As AeccDocument
Public g_oAeccDatabase As AeccDatabase


'
' Start Civil 3D and create Civil 3D document and database objects.
'
Public Function GetBaseCivilObjects() As Boolean
    Dim oApp As AcadApplication
    Set oApp = ThisDrawing.Application
    ' NOTE - Always specify the version number.
    Const sAppName = "AeccXUiLand.AeccApplication.10.0"
    Set g_oCivilApp = oApp.GetInterfaceObject(sAppName)
    If g_oCivilApp Is Nothing Then
        MsgBox "Error creating " & sAppName & ", exit."
        GetBaseCivilObjects = False
        Exit Function
    End If
    Set g_oDocument = g_oCivilApp.ActiveDocument
    Set g_oAeccDatabase = g_oDocument.Database
    GetBaseCivilObjects = True
End Function

Attribute VB_Name = "Globals"
'
' MODULE_ID {Globals.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

'
' Global constants used throughout the application.
'
Global Const SURFACE_NAME As String = "EG"
Public Const SITE_NAME As String = "Sample site"
Global Const ALIGNMENT_NAME As String = "Alignment01"
Global Const STYLE_NAME = "Sample alignment style 01"
Global Const LABEL_STYLE_SET_NAME = "Sample label style set 01"
Global Const PROFILE1_NAME As String = "Sample profile01"
Global Const PROFILE2_NAME As String = "Sample profile02"
Global Const PROFILE_STYLE_NAME = "Sample profile style 01"
Global Const PROFILE_VIEW_NAME = "Sample profile view 01"
Global Const PROFILE_VIEW_STYLE_NAME = "Sample profile view style 01"
Global Const PROFILE_LABEL_STYLE_SET_NAME = "Sample profile style set 01"
Global Const PROFILEVIEW_BAND_STYLE_NAME = "Sample band style set 01"
Global Const PROFILEVIEW_PROFILE_BAND_STYLE_NAME = "Profile band style 01"
Global Const PROFILEVIEW_HORIZONTAL_BAND_STYLE_NAME = "Horizontal band style 01"
Global Const PROFILEVIEW_VERTICAL_BAND_STYLE_NAME = "Vertical band style 01"
Global Const PROFILEVIEW_SUPERELEVATION_BAND_STYLE_NAME = "Superelevation band style 01"
Global Const LINE_STYLE = "Sample line 01"
Global Const BLOCK_STYLE = "Sample block 01"
Global Const TICK_STYLE = "Sample tick 01"
Global Const LINE_STYLE2 = "Sample line 02"
Global Const BLOCK_STYLE2 = "Sample block 02"
Global Const TICK_STYLE2 = "Sample tick 02"
Global Const CREST_LABEL_STYLE_SET = "Sample crest label set 01"
Global Const STATION_LABEL_STYLE_SET = "Sample station label set 01"

Attribute VB_Name = "IterateProfiles"
'
' MODULE_ID {IterateProfiles.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Displays information about each alignment and profile
' associated with the site returned from the GetSite()
' function.
'
' This is currently unused by the sample program.
'
Function IterateAlignmentProfiles() As Boolean
    ' Get the collection of alignments in the site.
    Dim oAlignments As AeccAlignments
    On Error Resume Next
    Set oAlignments = GetSite().Alignments
    On Error GoTo 0
    If ((oAlignments Is Nothing) Or (oAlignments.Count = 0)) Then
        Debug.Print "No alignments exist."
        IterateAlignmentProfiles = False
        Exit Function
    End If
    
    ' Display information for each alignment in the collection
    ' of alignments.
    Dim oAlignment As AeccAlignment
    For Each oAlignment In oAlignments
        Debug.Print "Alignment name: " & oAlignment.Name
        Debug.Print "Description: " & oAlignment.Description
        ' Go through each of the profiles that the alignment
        ' is associated with.
        Debug.Print "This alignment has " & oAlignment.Profiles.Count & " profiles."
        Dim oProfile As AeccProfile
        For Each oProfile In oAlignment.Profiles
            Debug.Print "  Profile Name: " & oProfile.Name
            Dim oVAlignment As AeccAlignment
            Set oVAlignment = oProfile.Alignment
            Debug.Print "  Profile alignment name: " & oVAlignment.Name
            Debug.Print "  Profile alignment description: " & oVAlignment.Description
            Debug.Print "There are " & oVAlignment.Entities.Count & " alignment sub entities."
            Dim oAlignmentEntity As AeccAlignmentEntity
            For Each oAlignmentEntity In oVAlignment.Entities
                Debug.Print "EntityId: " & oAlignmentEntity.Id
                If oAlignmentEntity.Type = aeccArc Then
                    Dim oCurve As AeccAlignmentCurve
                    Set oCurve = oAlignmentEntity
                    Debug.Print "  AeccAlignmentEntity type: AeccAlignmentCurve"
                    Debug.Print "  StartEasting: " & oCurve.StartEasting
                    Debug.Print "  StartNorthing: " & oCurve.StartNorthing
                    Debug.Print "  EndEasting: " & oCurve.EndEasting
                    Debug.Print "  EndNorthing: " & oCurve.EndNorthing
                    Debug.Print "  Length: " & oCurve.Length
                ElseIf oAlignmentEntity.Type = aeccParabola Then
                
                ElseIf oAlignmentEntity.Type = aeccSpiral Then
                
                ElseIf oAlignmentEntity.Type = aeccAsymmetric Then
                
                ElseIf oAlignmentEntity.Type = aeccSpiralCurveSpiralGroup Then
                
                ElseIf oAlignmentEntity.Type = aeccTangent Then
                    Dim oTang As AeccAlignmentTangent
                    Set oTang = oAlignmentEntity
                    Debug.Print "  AeccAlignmentEntity type: AeccAlignmentTangent"
                    Debug.Print "  StartEasting: " & oTang.StartEasting
                    Debug.Print "  StartNorthing: " & oTang.StartNorthing
                    Debug.Print "  EndEasting: " & oTang.EndEasting
                    Debug.Print "  EndNorthing: " & oTang.EndNorthing
                    Debug.Print "  Direction: " & oTang.Direction
                    Debug.Print "  Length: " & oTang.Length
                End If
            Next
        Next
    Next
End Function

Attribute VB_Name = "Profile"
'
' MODULE_ID {Profile.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'
' Create a profile based on the surface named SURFACE_NAME and
' the alignment
'
Public Function CreateProfile(oAlignment As AeccAlignment) As Boolean
    ' Check the existance of the global drawing objects.
    If (g_oAeccDatabase Is Nothing) Then
        CreateProfile = False
        Exit Function
    End If
    
    ' Get the specified surface.
    Dim oSurface As AeccSurface
    On Error Resume Next
    Set oSurface = g_oAeccDatabase.Surfaces.Item(SURFACE_NAME)
    On Error GoTo 0
    If (oSurface Is Nothing) Then
        Debug.Print "Surface " & SURFACE_NAME & " does not exist."
        CreateProfile = False
        Exit Function
    End If

    ' Get the alignment's collection of profiles.
    Dim oProfiles As AeccProfiles
    On Error Resume Next
    Set oProfiles = oAlignment.Profiles
    On Error GoTo 0
    If (oProfiles Is Nothing) Then
        Debug.Print "Error getting profiles collection"
        CreateProfile = False
        Exit Function
    End If

    ' Create a style to be used by this profile.
    Dim oProfileStyle As AeccProfileStyle
    If (CreateProfileStyle(PROFILE_STYLE_NAME) = False) Then
        MsgBox "Error creating profile style."
        CreateProfile = False
        Exit Function
    End If
    Set oProfileStyle = g_oDocument.LandProfileStyles.Item(PROFILE_STYLE_NAME)

    ' Create a profile based on the surface and alignment
    ' already retrieved from the drawing.
    Dim oProfile As AeccProfile
    On Error Resume Next
    Set oProfile = oProfiles.Item(PROFILE1_NAME)
    On Error GoTo 0
    If (oProfile Is Nothing) Then
        Set oProfile = oProfiles.AddFromSurface(PROFILE1_NAME, aeccExistingGround, oProfileStyle, oSurface.Name, oAlignment.StartingStation, oAlignment.EndingStation, "0")
        oProfile.Update
        If oProfile Is Nothing Then
            Debug.Print "Error creating an existing ground profile"
            CreateProfile = False
            Exit Function
        End If
    End If
    oProfile.ShowLabels = True
    oProfile.Style.LineDisplayStyleProfile.color = acRed


    ' Create a second profile for the same alignment, but
    ' this one based on entities that we will describe
    ' directly.
    ' Create the profile only if it has not already been created.
    Set oProfile = Nothing
    On Error Resume Next
    Set oProfile = oProfiles.Item(PROFILE2_NAME)
    On Error GoTo 0
    If (oProfile Is Nothing) Then
        ' old format: Set oProfile = oProfiles.Add(PROFILE2_NAME, aeccFinishedGround, oProfileStyle.Name, oAlignment.StartingStation, oAlignment.EndingStation, "0")
        Set oProfile = oProfiles.Add(PROFILE2_NAME, aeccFinishedGround, oProfileStyle.Name)
        ' Now we will add the entities that define the profile.
        ' NOTE: Profile entity points are not x,y,z point, but
        ' station-elevation locations.
        Dim dLoc1(0 To 1) As Double
        Dim dLoc2(0 To 1) As Double
        Dim oProfileTangent1 As aeccProfileTangent
        dLoc1(0) = oAlignment.StartingStation: dLoc1(1) = -40#
        dLoc2(0) = 758.2: dLoc2(1) = -70#
        Set oProfileTangent1 = oProfile.Entities.AddFixedTangent(dLoc1, dLoc2)
        
        Dim oProfileTangent2 As aeccProfileTangent
        dLoc1(0) = 1508.2: dLoc1(1) = -60#
        dLoc2(0) = oAlignment.EndingStation: dLoc2(1) = -4#
        Set oProfileTangent2 = oProfile.Entities.AddFixedTangent(dLoc1, dLoc2)
        
        Dim dCrestLen As Double
        dCrestLen = 900.1
        Call oProfile.Entities.AddFreeSymmetricParabolaByLength(oProfileTangent1.Id, oProfileTangent2.Id, aeccSag, dCrestLen, True)
        
        ' Print out all the PVIs that result from these
        ' new entities.
        Debug.Print "PVI count: "; oProfile.PVIs.Count
        Dim oPVI As AeccProfilePVI
        For Each oPVI In oProfile.PVIs
            Debug.Print "PVI  station:   "; oPVI.Station
            Debug.Print "     elevation: "; oPVI.Elevation
            Debug.Print
        Next
        
        ' Find the PVI close to station 1000 elevation -70.
        Set oPVI = Nothing
        Set oPVI = oProfile.PVIs.ItemAt(1000, -70)
        Debug.Print "PVI closest to station 1000 is at station: "; oPVI.Station
        
        ' Add another PVI and slightly adjust its elevation.
        Set oPVI = oProfile.PVIs.Add(607.4, -64.3, aeccProfileTangent)
        oPVI.Elevation = oPVI.Elevation - 2#
        
        oProfile.Update
    End If
    
    oProfile.ShowLabels = True
    oProfile.Style.LineDisplayStyleProfile.color = acRed
    
    oProfile.Update
    CreateProfile = True
End Function

Attribute VB_Name = "ProfileStyle"
'
' MODULE_ID {ProfileStyle.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create a profile style.
'
Public Function CreateProfileStyle(sStyleName As String) As Boolean
    ' Delete the style if it already exists.
    On Error Resume Next
    g_oDocument.ProfileStyles.Remove sStyleName
    On Error GoTo 0
    
    ' Create a new style and add it to the drawing's collection
    ' of profile styles.
    Dim oProfileStyle As AeccProfileStyle
    On Error Resume Next
    Set oProfileStyle = g_oDocument.LandProfileStyles.Add(PROFILE_STYLE_NAME)
    On Error GoTo 0
    If (oProfileStyle Is Nothing) Then
        On Error Resume Next
        Set oProfileStyle = g_oDocument.LandProfileStyles.Item(PROFILE_STYLE_NAME)
        On Error GoTo 0
        If (oProfileStyle Is Nothing) Then
            MsgBox "Error creating profile style."
            CreateProfileStyle = False
            Exit Function
        End If
    End If
    
    ' Now set the style.
    oProfileStyle.ArrowDisplayStyleProfile.color = 140 ' orange
    oProfileStyle.ArrowDisplayStyleProfile.LinetypeScale = 200
    oProfileStyle.ArrowDisplayStyleProfile.Visible = True
    
    oProfileStyle.AsymmetricalParabolaDisplayStyleProfile.color = 140 ' slate
    oProfileStyle.CurveDisplayStyleProfile.color = 190 ' purple
    oProfileStyle.LineDisplayStyleProfile.color = 210 ' pink
    oProfileStyle.LineExtensionDisplayStyleProfile.color = 50 ' yellow
    oProfileStyle.ParabolicCurveExtensionDisplayStyleProfile.color = 130 ' light blue
    oProfileStyle.SymmetricalParabolaDisplayStyleProfile.color = 110 ' turq
    
    CreateProfileStyle = True
End Function

Attribute VB_Name = "ProfileView"
'
' MODULE_ID {ProfileView.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Display a graphical representation of the profile we have
' created in oAlignment.
'
Public Function CreateProfileView(oAlignment As AeccAlignment) As Boolean
    ' Set the location to put our profile view.
    Dim dOriginPt(0 To 2) As Double
    dOriginPt(0) = 6500#  ' to the right of the surface
    dOriginPt(1) = 4200#  ' slightly higher than the surface

    ' Make a style for the profile view.
    Dim oPVStyle As AeccProfileViewStyle
    If (CreateProfileViewStyle(PROFILE_VIEW_STYLE_NAME) = False) Then
        MsgBox "Error accessing profile view style."
        CreateProfileView = False
        Exit Function
    End If
    Set oPVStyle = g_oDocument.ProfileViewStyles.Item(PROFILE_VIEW_STYLE_NAME)

    ' Create a band style for the profile view
    Dim oPVBandStyleSet As AeccProfileViewBandStyleSet
    If (CreateBandStyleSet(PROFILEVIEW_BAND_STYLE_NAME) = False) Then
        Debug.Print "Error accessing default profile view band style set."
        CreateProfileView = False
        Exit Function
    End If
    Set oPVBandStyleSet = g_oDocument.ProfileViewBandStyleSets.Item(PROFILEVIEW_BAND_STYLE_NAME)

    ' First check to see if a profile view with our name
    ' already exists.
    Dim oProfileView As AeccProfileView
    On Error Resume Next
    Set oProfileView = oAlignment.ProfileViews.Item(PROFILE_VIEW_NAME)
    On Error GoTo 0
    If oProfileView Is Nothing Then
        ' Create the profile view and add it to the alignment's
        ' collection of profile views.
        Set oProfileView = oAlignment.ProfileViews.Add(PROFILE_VIEW_NAME, "0", dOriginPt, oPVStyle, oPVBandStyleSet)
    End If
    oProfileView.Description = "Profile view of alignment '" & oAlignment.Name & "'"
    
    oProfileView.Style = g_oDocument.ProfileViewStyles.Item(PROFILE_VIEW_STYLE_NAME)
    
    CreateProfileView = True
End Function

Attribute VB_Name = "ProfileViewStyle"
'
' MODULE_ID {ProfileViewStyle.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'

'
' Create a style for the profile view.  This style will
' modify the top and bottom axes, the grid style,
' and the horizontal grid lines properties from
' whatever the standard grid style is.
'
Function CreateProfileViewStyle(sStyleName As String) As Boolean
    ' First we check to see if a style with this name already exists.
    ' If so we will erase it.
    Dim oProfileViewStyle As AeccProfileViewStyle
    On Error Resume Next
    Set oProfileViewStyle = g_oDocument.ProfileViewStyles.Item(sStyleName)
    On Error GoTo 0
    If (Not oProfileViewStyle Is Nothing) Then
        ' If it is in use, it cannot be removed and will error
        ' on any attempt to do so.  We will catch the errors
        ' and do nothing if one takes place.
        On Error Resume Next
        g_oDocument.ProfileViewStyles.Remove sStyleName
        On Error GoTo 0
    End If

    ' Make a new profile view style and attach it to the
    ' drawing's collection of profile view styles.
    On Error Resume Next
    Set oProfileViewStyle = g_oDocument.ProfileViewStyles.Add(sStyleName)
    On Error GoTo 0
    If (oProfileViewStyle Is Nothing) Then
        CreateProfileViewStyle = False
        Exit Function
    End If
    ' This style automatically has the features of the standard
    ' profile view style for the drawing.
    
    '' Some information:
    '' Vertical lines in the graph are based on the bottom axis
    '' interval.  Top axis intervals only matter for how the
    '' tick marks are placed along the top axis.
    
    ' We will first adjust how the bottom axis is displayed.
    ' This involves setting the properties of a number of
    ' subobjects, each of which describes how a feature of the
    ' bottom axis is displayed.
    
    ' First, adjust the bottom axis.  We will put station
    ' information here, with the title at the far left.
    With oProfileViewStyle.BottomAxis
        .DisplaySyle2d.color = 60
        .DisplaySyle2d.Visible = True
        .MajorTickStyle.Size = 0.01
        ' NOTE: See Chapter 54 (Sections Dialog Boxes) for
        ' information about the name template.
        .MajorTickStyle.Text = "<[Station Value(Uft|FS|P2|RN|Sn|OF|AP|B2|TP|EN|W0|DZY)]>"
        .MajorTickStyle.Interval = 50 ' feet, in documents that use Imperial measures
        Dim dPoint(0 To 2) As Double
        dPoint(0) = -0.13
        dPoint(1) = 0#
        .TitleStyle.Offset = dPoint
        .TitleStyle.Text = "Stations"
        .TitleStyle.Position = aeccStart
    End With

    ' Now the top axis.  We will use this to mark meters
    ' from the start of the profile at an interval that
    ' is markedly different than the bottom axis.
    '
    ' Linetype lets you select among the types of lines loaded
    ' into the drawing or from .lin files.
    With oProfileViewStyle.TopAxis
        .DisplaySyle2d.Visible = True
        ' We will modify the text to display yards in decimal
        ' format, instead of the more usual feet in station format.
        .MajorTickStyle.Text = "<[Station Value(Um|FD|P1|RN|Sn|OF|AP|B2|TP|EN|W0|DZY)]> meters"
        .MajorTickStyle.Interval = 164.041995  ' 50 meters, in feet
        .TitleStyle.Text = "Meters"
        .TitleStyle.Position = aeccStart
    End With

    ' Now the properties of the graph.
    With oProfileViewStyle.GraphStyle
        .TitleStyle.Text = "Profile View of:<[Parent Alignment(CP)]>"
        .VerticalExaggeration = 5
        .Direction = aeccLeftToRight
        .GridStyle.GridsAboveMaxElevation = 1
        .GridStyle.GridsBelowDatum = 1
    End With

    ' And the properties of the lines of the graph that are
    ' drawn at each geometric change in the profile.
    With oProfileViewStyle.GridAtHGPDisplayStylePlan
        Dim oTrueColor As New AcadAcCmColor
        oTrueColor.SetRGB 5, 15, 254
        Set .TrueColor = oTrueColor
        
        'To use Linetypes from file, we have to load them first
        ThisDrawing.Linetypes.Load "DOT", "acad.lin"
        If Err.Description <> "" Then
            MsgBox Err.Description
        Else
            .Linetype = "DOT"
        End If
        
        .Visible = True
    End With

    CreateProfileViewStyle = True
End Function ' CreateProfileViewStyle


'
' Create a profile label style set.  This is a set of
' styles that control how the various labels are formatted.
'
' NOTE: This function is not called, and there is no
' way to use a profile label style set from within
' the API.  The set can only be assigned to a profile
' through the user interface.
'
Public Function CreateProfileLabelStyleSet(sStyleName As String) As Boolean
    Dim i As Integer
    
    ' Add a new AeccAlignmentLabelStyleSet in the document's
    ' collection of AlignmentStyleSet objects, after first
    ' deleting any older version of the style set that might
    ' exist.
    Dim oProfileLabelStyleSet As AeccProfileLabelStyleSet
    Set oProfileLabelStyleSet = Nothing
    On Error Resume Next
    g_oDocument.ProfileLabelStyleSets.Remove (sStyleName)
    On Error GoTo 0
    Set oProfileLabelStyleSet = g_oDocument.ProfileLabelStyleSets.Add(sStyleName)
    If (oProfileLabelStyleSet Is Nothing) Then
        Debug.Print "Error setting a Profile Label Style Set: " & Err.Description
        Err.Clear
        CreateProfileLabelStyleSet = vbNullString
        Exit Function
    End If
    ' Assign some profile label styles.
    oProfileLabelStyleSet.Description = "This is an overly complicated style set used as a demonstration."

    Dim oCrestCurveStyle As AeccLabelStyleSetItem
    Dim oLabelStyle As AeccLabelStyle
    Dim oLabelStyleTickComponent As AeccLabelStyleTickComponent
    Dim oLabelStyleLineComponent As AeccLabelStyleLineComponent
    Dim oLabelStyleTextComponent As AeccLabelStyleTextComponent
    Dim oLabelStyleBlockComponent As AeccLabelStyleBlockComponent
    
    ' -------------------------------------------------------
    ' This section demonstrates how to set the crest curve
    ' label style.  Sag curve and geometry point labels are
    ' similarly structured.

    ' Create a new label style for our crest curves and
    ' add it to the drawing's collection of profile label
    ' styles.
    On Error Resume Next
    g_oDocument.ProfileLabelStyles.CurveLabelStyles.Remove CREST_LABEL_STYLE_SET
    Set oLabelStyle = g_oDocument.ProfileLabelStyles.CurveLabelStyles.Item(CREST_LABEL_STYLE_SET)
    On Error GoTo 0
    If (oLabelStyle Is Nothing) Then
        Set oLabelStyle = g_oDocument.ProfileLabelStyles.CurveLabelStyles.Add(CREST_LABEL_STYLE_SET)
    End If

    ' Add to the AeccLabelStyle object an object for managing
    ' the style of label ticks.  This style governs the
    ' properties of the tick mark placed at regular intervals
    ' (in this case, at every station).
    On Error Resume Next
    oLabelStyle.TickComponents.Remove TICK_STYLE
    Set oLabelStyleTickComponent = oLabelStyle.TickComponents.Item(TICK_STYLE)
    On Error GoTo 0
    If (oLabelStyleTickComponent Is Nothing) Then
        Set oLabelStyleTickComponent = oLabelStyle.TickComponents.Add(TICK_STYLE)
    End If
    ' Specify what kind of symbol is used for the tick.
    oLabelStyleTickComponent.BlockName = "AeccTickLine"
    oLabelStyleTickComponent.Lineweight.Value = 60 ' .60 mm
    oLabelStyleTickComponent.AlignWithObject = True ' perpendicular to alignment
    oLabelStyleTickComponent.Angle = 0# ' in degrees
    oLabelStyleTickComponent.Visibility = True
    
    ' Add a line style to the crest curve style set.  This
    ' style governs the properties of a line placed at each
    ' crest curve.
    On Error Resume Next
    oLabelStyle.LineComponents.Remove LINE_STYLE
    Set oLabelStyleLineComponent = oLabelStyle.LineComponents.Item(LINE_STYLE)
    On Error GoTo 0
    If (oLabelStyleLineComponent Is Nothing) Then
        Set oLabelStyleLineComponent = oLabelStyle.LineComponents.Add(LINE_STYLE)
    End If
    oLabelStyleLineComponent.color = 40 ' orange-yellow
    oLabelStyleLineComponent.Angle = 2.094 ' radians, = 120 degrees
    oLabelStyleLineComponent.Length = -0.015 ' in whatever units are used in the drawing
    oLabelStyleLineComponent.StartPointXOffset = 0.0005
    oLabelStyleLineComponent.StartPointYOffset = 0
    oLabelStyleLineComponent.Visibility = True

    ' Add a line style to the crest curve style set.  This
    ' style governs the properties of a symbol placed at each
    ' crest curve. We will use this to add a circular tick
    ' mark.
    On Error Resume Next
    oLabelStyle.BlockComponents.Remove BLOCK_STYLE
    Set oLabelStyleBlockComponent = oLabelStyle.BlockComponents.Item(BLOCK_STYLE)
    On Error GoTo 0
    If (oLabelStyleBlockComponent Is Nothing) Then
        Set oLabelStyleBlockComponent = oLabelStyle.BlockComponents.Add(BLOCK_STYLE)
    End If
    oLabelStyleBlockComponent.BlockName = "AeccTickCircle"
    oLabelStyleBlockComponent.Visibility = True
    
    
    ' The major station label style automatically comes with a
    ' TextComponent named "Station".  Text componets like this
    ' one are for specifying what text is displayed at each
    ' station, and for managing how that text looks.  We will
    ' change what text is displayed, and move it under and to
    ' the side of each station anchor.
    
    Set oLabelStyleTextComponent = oLabelStyle.TextComponents.Item(0)
    ' Curve the text to follow the curves of the alignment.
    oLabelStyleTextComponent.AllowToCurve = True
    oLabelStyleTextComponent.Angle = 0#
    oLabelStyleTextComponent.XOffset = 0.01
    oLabelStyleTextComponent.YOffset = -0.015 - oLabelStyleTextComponent.Height
    oLabelStyleTextComponent.Contents = "STA=<[Station Value(Uft|FS|P2|RN|AP|Sn|TP|B2|EN|W0|OF)]>"
    oLabelStyleTextComponent.color = 253 ' light grey

    ' End of setting the crest curve style set.
    ' -------------------------------------------------------

    Set oCrestCurveStyle = oProfileLabelStyleSet.CrestCurvesLabelStyleSet.Add(oLabelStyle)
    oCrestCurveStyle.DimensionAnchorOption = aeccLabelAnchorDistanceAbove
    oCrestCurveStyle.DimensionAnchorValue = 0


    ' -------------------------------------------------------
    ' This section demonstrates how to set the major station
    ' label style.

    Dim oMajorStationStyle As AeccLabelStyleSetItem

    ' Create a new label style for our crest curves and
    ' add it to the drawing's collection of profile label
    ' styles.
    Set oLabelStyle = Nothing
    On Error Resume Next
    g_oDocument.ProfileLabelStyles.MajorStationLabelStyles.Remove STATION_LABEL_STYLE_SET
    Set oLabelStyle = g_oDocument.ProfileLabelStyles.MajorStationLabelStyles.Item(STATION_LABEL_STYLE_SET)
    On Error GoTo 0
    If (oLabelStyle Is Nothing) Then
        Set oLabelStyle = g_oDocument.ProfileLabelStyles.MajorStationLabelStyles.Add(STATION_LABEL_STYLE_SET)
    End If

    ' Add a line style to the crest curve style set.  This
    ' style governs the properties of a line placed at each
    ' crest curve.
    On Error Resume Next
    oLabelStyle.LineComponents.Remove LINE_STYLE2
    Set oLabelStyleLineComponent = oLabelStyle.LineComponents.Item(LINE_STYLE2)
    On Error GoTo 0
    If (oLabelStyleLineComponent Is Nothing) Then
        Set oLabelStyleLineComponent = oLabelStyle.LineComponents.Add(LINE_STYLE2)
    End If
    oLabelStyleLineComponent.color = 40 ' orange-yellow
    oLabelStyleLineComponent.Angle = 2.094 ' radians, = 120 degrees
    oLabelStyleLineComponent.Length = -0.015 ' in whatever units are used in the drawing
    oLabelStyleLineComponent.StartPointXOffset = 0.0005
    oLabelStyleLineComponent.StartPointYOffset = 0
    oLabelStyleLineComponent.Visibility = True

    ' Add a line style to the crest curve style set.  This
    ' style governs the properties of a symbol placed at each
    ' crest curve. We will use this to add a circular tick
    ' mark.
    On Error Resume Next
    oLabelStyle.BlockComponents.Remove BLOCK_STYLE2
    Set oLabelStyleBlockComponent = oLabelStyle.BlockComponents.Item(BLOCK_STYLE2)
    On Error GoTo 0
    If (oLabelStyleBlockComponent Is Nothing) Then
        Set oLabelStyleBlockComponent = oLabelStyle.BlockComponents.Add(BLOCK_STYLE2)
    End If
    oLabelStyleBlockComponent.BlockName = "AeccTickCircle"
    oLabelStyleBlockComponent.Visibility = True
    
    
    ' The major station label style automatically comes with a
    ' TextComponent named "Station".  Text componets like this
    ' one are for specifying what text is displayed at each
    ' station, and for managing how that text looks.  We will
    ' change what text is displayed, and move it under and to
    ' the side of each station anchor.
    
    Set oLabelStyleTextComponent = oLabelStyle.TextComponents.Item(0)
    ' Curve the text to follow the curves of the alignment.
    oLabelStyleTextComponent.AllowToCurve = True
    oLabelStyleTextComponent.Angle = 0#
    oLabelStyleTextComponent.XOffset = 0.01
    oLabelStyleTextComponent.YOffset = -0.015 - oLabelStyleTextComponent.Height
    oLabelStyleTextComponent.Contents = "STA=<[Station Value(Uft|FS|P2|RN|AP|Sn|TP|B2|EN|W0|OF)]>"
    oLabelStyleTextComponent.color = 253 ' light grey
    oLabelStyleTextComponent.Visibility = True

    ' End of setting the crest curve style set.
    ' -------------------------------------------------------

    '
    Dim oMajorStationLabelStyleSet As AeccLabelMajorStationStyleSetItem
    Dim dIncrement As Double
    dIncrement = 50#
    For i = 0 To oProfileLabelStyleSet.MajorStationLabelStyleSet.Count - 1
        If (oProfileLabelStyleSet.MajorStationLabelStyleSet.Item(i).Style.Name = oLabelStyle.Name) Then
            oProfileLabelStyleSet.MajorStationLabelStyleSet.Remove i
        End If
    Next i
    Set oMajorStationLabelStyleSet = oProfileLabelStyleSet.MajorStationLabelStyleSet.Add(oLabelStyle, dIncrement)

    CreateProfileLabelStyleSet = True
End Function ' CreateProfileLabelStyleSet


'
' Create a band style set.  This is a set of styles that
' control how the data bands are formatted.
'
Public Function CreateBandStyleSet(sStyleName As String) As Boolean
    ' Remove any old band style set with the same name that
    ' might exist and create a new band.  It might be that
    ' the style is in use, and cannot be removed.  In that
    ' case, we will use the existing style.  We use the
    ' name given to us in the sStyleName parameter so that
    ' the calling function knows what name the style set
    ' is, and can access it.
    Dim oPVBandStyleSet As AeccProfileViewBandStyleSet
    On Error Resume Next
    g_oDocument.ProfileViewBandStyleSets.Remove sStyleName
    Set oPVBandStyleSet = g_oDocument.ProfileViewBandStyleSets.Add(sStyleName)
    On Error GoTo 0
    If (oPVBandStyleSet Is Nothing) Then
        On Error Resume Next
        Set oPVBandStyleSet = g_oDocument.ProfileViewBandStyleSets.Item(sStyleName)
        On Error GoTo 0
        If (oPVBandStyleSet Is Nothing) Then
            Debug.Print "Error trying to create a band style set."
            CreateBandStyleSet = False
            Exit Function
        End If
    End If

    ''''''''''''''''''''''''''''''''''''''''''''''''
    ' Add a profile information data band
    
    ' We will modify the style set by adding a profile
    ' band - a band that describes basic information of
    ' profile geometry at station tick marks.
    '
    ' Remove any old profile band styles that might exist
    ' and create a new style.  It might be that the style
    ' is in use, and cannot be removed.  In that case, we
    ' will use the existing style.
    Dim oBandProfileDataStyle As AeccBandProfileDataStyle
    On Error Resume Next
    g_oDocument.ProfileViewBandStyles.ProfileDataBandStyles.Remove PROFILEVIEW_PROFILE_BAND_STYLE_NAME
    Set oBandProfileDataStyle = g_oDocument.ProfileViewBandStyles.ProfileDataBandStyles.Add(PROFILEVIEW_PROFILE_BAND_STYLE_NAME)
    On Error GoTo 0
    If (oBandProfileDataStyle Is Nothing) Then
        On Error Resume Next
        Set oBandProfileDataStyle = g_oDocument.ProfileViewBandStyles.ProfileDataBandStyles.Item(PROFILEVIEW_PROFILE_BAND_STYLE_NAME)
        On Error GoTo 0
        If (oBandProfileDataStyle Is Nothing) Then
            Debug.Print "Error trying to create a profile band style."
            CreateBandStyleSet = False
            Exit Function
        End If
    End If

    ' Add ticks and labels to each horizontal geography location.
    With oBandProfileDataStyle
        .HGPLabelDisplayStylePlan.Visible = True
        .HGPTickDisplayStylePlan.color = 10 ' red
        .HGPTickDisplayStylePlan.Visible = True
        .HGPLabelStyle.TextComponents.Item(0).Contents = "<[Station Value(Uft|FS|P0|RN|AP|Sn|TP|B2|EN|W0|OF)]>"
        .HGPLabelStyle.TextComponents.Item(0).color = 11 ' light red
        .HGPLabelStyle.TextComponents.Item(0).Visibility = True
    End With
    
    ' Modify how the title is displayed.
    With oBandProfileDataStyle
        .TitleBoxDisplayStylePlan.color = 10 ' red
        .TitleBoxDisplayStylePlan.Linetype = "DOT"
        .TitleBoxDisplayStylePlan.Visible = True
        .TitleBoxTextDisplayStylePlan.color = 80 ' green
        .TitleBoxTextDisplayStylePlan.Visible = True
        .TitleStyle.Text = "Profile Info"
        .TitleStyle.TextHeight = 0.0125
        .TitleStyle.TextBoxWidth = 0.21
    End With
    
    ' Hide the rest of the information locations.
    With oBandProfileDataStyle
        .VGPLabelStyle.TextComponents.Item(0).Visibility = False
        .MajorIncrementLabelStyle.TextComponents.Item(0).Visibility = False
        .MajorStationLabelDisplayStylePlan.Visible = False
        .MajorTickDisplayStylePlan.Visible = False
        .MinorIncrementLabelStyle.TextComponents.Item(0).Visibility = False
        .MinorStationLabelDisplayStylePlan.Visible = False
        .MinorTickDisplayStylePlan.Visible = False
        .VGPLabelDisplayStylePlan.Visible = False
        .VGPTickDisplayStylePlan.Visible = False
        .StationEquationLabelStyle.TextComponents.Item(0).Visibility = True
        .StationEquationLabelDisplayStylePlan.Visible = True
        .StationEquationTickDisplayStylePlan.Visible = True
    End With
    
    ' Finally, we add the profile information style to
    ' the profile view style set we created earlier.
    Dim oBandStyleSetItem As AeccBandStyleSetItem
    Set oBandStyleSetItem = oPVBandStyleSet.Add(oBandProfileDataStyle)
    
    
    ''''''''''''''''''''''''''''''''''''''''''''''''
    ' Add a horizontal geometry data band
    
    ' We will modify the style set by adding a geometry
    ' band - a band that describes the horizontal slopes
    ' of each segment of the profile geometry.
    '
    ' Remove any old horizontal geometry band styles that
    ' might exist and create a new style.  It might be
    ' that the style is in use, and cannot be removed.  In
    ' that case, we will use the existing style.
    Dim oBandHorizontalGeometryStyle As AeccBandHorizontalGeometryStyle
    On Error Resume Next
    g_oDocument.ProfileViewBandStyles.HorizontalGeometryBandStyles.Remove PROFILEVIEW_HORIZONTAL_BAND_STYLE_NAME
    Set oBandHorizontalGeometryStyle = g_oDocument.ProfileViewBandStyles.HorizontalGeometryBandStyles.Add(PROFILEVIEW_HORIZONTAL_BAND_STYLE_NAME)
    On Error GoTo 0
    If (oBandHorizontalGeometryStyle Is Nothing) Then
        On Error Resume Next
        Set oBandHorizontalGeometryStyle = g_oDocument.ProfileViewBandStyles.HorizontalGeometryBandStyles.Item(PROFILEVIEW_HORIZONTAL_BAND_STYLE_NAME)
        On Error GoTo 0
        If (oBandHorizontalGeometryStyle Is Nothing) Then
            Debug.Print "Error trying to create a horizontal band style."
            CreateBandStyleSet = False
            Exit Function
        End If
    End If

    With oBandHorizontalGeometryStyle
        ' Add displays and labels for alignment tangents.
        .TangentGeometryDisplayStylePlan.Visible = True
        .TangentGeometryDisplayStylePlan.color = 160 ' blue
        .TangentLabelDisplayStylePlan.Visible = True
        .TangentLabelStyle.TextComponents.Item(0).Contents = "Length = <[Length(Uft|P2|RN|Sn|OF|AP)]>"
        .TangentLabelStyle.TextComponents.Item(0).color = 120 ' light blue
        .TangentLabelStyle.TextComponents.Item(0).Visibility = True
    
        ' Add displays and labels for alignment curves.
        .CurveGeometryDisplayStylePlan.Visible = True
        .CurveGeometryDisplayStylePlan.color = 160 ' blue
        .CurveLabelDisplayStylePlan.Visible = True
        .CurveLabelStyle.TextComponents.Item(0).Contents = "Length = <[Length(Uft|P2|RN|Sn|OF|AP)]>"
        .CurveLabelStyle.TextComponents.Item(0).color = 120 ' light blue
        .CurveLabelStyle.TextComponents.Item(0).Visibility = True
    
        ' Add tick marks at each horizontal geometry point,
        ' the location where different segments of the
        ' alignment meet.  Make it the same color as the
        ' horizontal geometry points in the first data band.
        .TickDisplayStylePlan.color = 10 ' red
        .TickDisplayStylePlan.Visible = True
        
        ' Modify how the title is displayed.
        .TitleBoxDisplayStylePlan.color = 10 ' red
        .TitleBoxDisplayStylePlan.Linetype = "DOT"
        .TitleBoxDisplayStylePlan.Visible = True
        .TitleBoxTextDisplayStylePlan.color = 80 ' green
        .TitleBoxTextDisplayStylePlan.Visible = True
        .TitleStyle.Text = "Alignment Geometry"
        .TitleStyle.TextHeight = 0.0125
        .TitleStyle.TextBoxWidth = 0.21
        
        ' Hide the rest of the information locations and
        ' graphical displays.
        .SpiralGeometryDisplayStylePlan.Visible = False
        .SpiralLabelDisplayStylePlan.Visible = False
    End With
    
    ' Finally, we add the vertical geometry style to the
    ' profile view style set we created earlier.
    Set oBandStyleSetItem = oPVBandStyleSet.Add(oBandHorizontalGeometryStyle)


    ''''''''''''''''''''''''''''''''''''''''''''''''
    ' Add a Vertical Geometry data band
    
    ' We will modify the style set by adding a geometry
    ' band - a band that describes the vertical slopes
    ' of each segment of the profile geometry.
    '
    ' Remove any old vertical geometry band styles that
    ' might exist and create a new style.  It might be
    ' that the style is in use, and cannot be removed.  In
    ' that case, we will use the existing style.
    Dim oBandVerticalGeometryStyle As AeccBandVerticalGeometryStyle
    On Error Resume Next
    g_oDocument.ProfileViewBandStyles.VerticalGeometryBandStyles.Remove PROFILEVIEW_VERTICAL_BAND_STYLE_NAME
    Set oBandVerticalGeometryStyle = g_oDocument.ProfileViewBandStyles.VerticalGeometryBandStyles.Add(PROFILEVIEW_VERTICAL_BAND_STYLE_NAME)
    On Error GoTo 0
    If (oBandVerticalGeometryStyle Is Nothing) Then
        On Error Resume Next
        Set oBandVerticalGeometryStyle = g_oDocument.ProfileViewBandStyles.VerticalGeometryBandStyles.Item(PROFILEVIEW_VERTICAL_BAND_STYLE_NAME)
        On Error GoTo 0
        If (oBandVerticalGeometryStyle Is Nothing) Then
            Debug.Print "Error trying to create a vertical band style."
            CreateBandStyleSet = False
            Exit Function
        End If
    End If

    With oBandVerticalGeometryStyle
        ' Add graphical marks that show the uphill or downhill
        ' directions and the lengths of the vertical segments
        ' of the profile.  On uphill sections the label of the
        ' length of the segment will be in white, on downhill
        ' it will be pale yellow.
        .DownhillTangentLabelStyle.TextComponents.Item(0).Contents = "<[Tangent Horizontal Length(Uft|P2|RN|Sn|OF|AP)]>"
        .DownhillTangentLabelStyle.TextComponents.Item(0).color = 51 ' pale yellow
        .DownhillTangentLabelStyle.TextComponents.Item(0).Visibility = True
        .UphillTangentLabelStyle.TextComponents.Item(0).Contents = "<[Tangent Horizontal Length(Uft|P2|RN|Sn|OF|AP)]>"
        .UphillTangentLabelStyle.TextComponents.Item(0).color = 255  ' white
        .UphillTangentLabelStyle.TextComponents.Item(0).Visibility = True
        .TangentGeometryDisplayStylePlan.color = 220 ' pink
        .TangentGeometryDisplayStylePlan.Visible = True
        .TangentLabelDisplayStylePlan.Visible = True
        .TangentGeometryDisplayStylePlan.Visible = True
        
        ' Modify how the title is displayed.
        .TitleBoxDisplayStylePlan.color = 10 ' red
        .TitleBoxDisplayStylePlan.Linetype = "DOT"
        .TitleBoxDisplayStylePlan.Visible = True
        .TitleBoxTextDisplayStylePlan.color = 80 ' green
        .TitleBoxTextDisplayStylePlan.Visible = True
        .TitleStyle.Text = "Profile Geometry"
        .TitleStyle.TextHeight = 0.0125
        .TitleStyle.TextBoxWidth = 0.21
    
        ' Hide the rest of the information locations and
        ' graphical displays.
        .CurveGeometryDisplayStylePlan.Visible = False
        .CurveLabelDisplayStylePlan.Visible = False
        .TickDisplayStylePlan.Visible = False
    End With
    
    ' Finally, we add the vertical geometry style to the
    ' profile view style set we created earlier.
    Set oBandStyleSetItem = oPVBandStyleSet.Add(oBandVerticalGeometryStyle)


    ''''''''''''''''''''''''''''''''''''''''''''''''
    ' Add a Superelevation data band
    
    ' We will modify the style set by adding a
    ' superelevation band - a band that describes the
    ' superelevation of the alignment along the length
    ' of the profile view.
    '
    ' Remove any old superelevation geometry band styles
    ' that might exist and create a new style.  It might
    ' be that the style is in use, and cannot be removed.
    ' In that case, we will use the existing style.
    Dim oBandSuperElevationStyle As AeccBandSuperElevationStyle
    On Error Resume Next
    g_oDocument.ProfileViewBandStyles.SuperElevationBandStyles.Remove PROFILEVIEW_SUPERELEVATION_BAND_STYLE_NAME
    Set oBandSuperElevationStyle = g_oDocument.ProfileViewBandStyles.SuperElevationBandStyles.Add(PROFILEVIEW_SUPERELEVATION_BAND_STYLE_NAME)
    On Error GoTo 0
    If (oBandSuperElevationStyle Is Nothing) Then
        On Error Resume Next
        Set oBandSuperElevationStyle = g_oDocument.ProfileViewBandStyles.SuperElevationBandStyles.Item(PROFILEVIEW_SUPERELEVATION_BAND_STYLE_NAME)
        On Error GoTo 0
        If (oBandSuperElevationStyle Is Nothing) Then
            Debug.Print "Error trying to create a superelevation band style."
            CreateBandStyleSet = False
            Exit Function
        End If
    End If

    With oBandSuperElevationStyle
        ' Add graphical display of the slope of the
        ' left and right outside shoulders.  If the
        ' line is above the centerline, then the slope
        ' is positive.
        .LeftOutsideShoulderLineDisplayStylePlan.Visible = True
        .LeftOutsideShoulderLineDisplayStylePlan.color = 151 ' pale blue
        .RightOutsideShoulderLineDisplayStylePlan.Visible = True
        .RightOutsideShoulderLineDisplayStylePlan.color = 51 ' pale yellow
        
        ' Add a reference line through the center of the
        ' data band.
        .ReferenceLineDisplayStylePlan.Visible = True
        .ReferenceLineDisplayStylePlan.color = 252 ' gray
        
        ' Display a marker when the crown returns to
        ' normal.
        .NormalCrownLabelDisplayStylePlan.Visible = True
        .NormalCrownTickDisplayStylePlan.Visible = True
        .NormalCrownLocationLabelStyle.TextComponents.Item(0).Contents = "Begin Normal - <[Station Value(Uft|FS|P2|RN|AP|Sn|TP|B2|EN|W0|OF)]>"

        ' Modify how the title is displayed.
        .TitleBoxDisplayStylePlan.color = 10 ' red
        .TitleBoxDisplayStylePlan.Linetype = "DOT"
        .TitleBoxDisplayStylePlan.Visible = True
        .TitleBoxTextDisplayStylePlan.color = 80 ' green
        .TitleBoxTextDisplayStylePlan.Visible = True
        .TitleStyle.Text = "Profile Geometry"
        .TitleStyle.TextHeight = 0.0125
        .TitleStyle.TextBoxWidth = 0.21
    
        ' Hide the rest of the information locations and
        ' graphical displays.
        '.LeftOutsideShoulderLineDisplayStylePlan.Visible = False
        '.RightOutsideShoulderLineDisplayStylePlan.Visible = False
        '.ReferenceLineDisplayStylePlan.Visible = False
        '.NormalCrownLabelDisplayStylePlan.Visible = False
        '.NormalCrownTickDisplayStylePlan.Visible = False
        .FullSuperLabelDisplayStylePlan.Visible = False
        .FullSuperTickDisplayStylePlan.Visible = False
        .LeftInsidePavementLineDisplayStylePlan.Visible = False
        .LeftInsideShoulderLineDisplayStylePlan.Visible = False
        .LeftOutsidePavementLineDisplayStylePlan.Visible = False
        .LevelCrownLabelDisplayStylePlan.Visible = False
        .LevelCrownTickDisplayStylePlan.Visible = False
        .ReverseCrownLabelDisplayStylePlan.Visible = False
        .ReverseCrownTickDisplayStylePlan.Visible = False
        .RightInsidePavementLineDisplayStylePlan.Visible = False
        .RightInsideShoulderLineDisplayStylePlan.Visible = False
        .RightOutsidePavementLineDisplayStylePlan.Visible = False
        .ShoulderBreakOverLabelDisplayStylePlan.Visible = False
        .ShoulderBreakOverTickDisplayStylePlan.Visible = False
        .TransitionSegmentLabelDisplayStylePlan.Visible = False
    End With

    ' Finally, we add the superelevation style to the
    ' profile view style set we created earlier.
    Set oBandStyleSetItem = oPVBandStyleSet.Add(oBandSuperElevationStyle)


    ''''''''''''''''''''''''''''''''''''''''''''''''
    ' We are done.  Return true.
    CreateBandStyleSet = True
End Function ' CreateBandStyleSet

Attribute VB_Name = "Site"
'
' MODULE_ID {Site.bas}
' {ProfileSample.dvb}
'
' Copyright {2003-2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create an AeccSite object.
'
Public Function CreateSite() As Boolean
    On Error Resume Next
    
    Dim oSites As AeccSites
    Set oSites = g_oDocument.Sites
    Dim oSite As AeccSite

    Set oSite = oSites.Item(SITE_NAME)
    If oSite Is Nothing Then
        Set oSite = oSites.Add(SITE_NAME)
        If oSite Is Nothing Then
            Debug.Print "Error creating " & SITE_NAME
            CreateSite = False
            Exit Function
        End If
    End If
    CreateSite = True
End Function
    

'
' Get a site with the name
'
Public Function GetSite() As AeccSite
    Dim oSites As AeccSites
    Dim oSite As AeccSite
    
    On Error Resume Next
    Set oSites = g_oDocument.Sites
    If (Not oSites Is Nothing) Then
        Set oSite = oSites.Item(SITE_NAME)
        If (oSite Is Nothing) Then
            Set GetSite = Nothing
        Else
            Set GetSite = oSite
        End If
    End If
End Function

Attribute VB_Name = "Subroutines"
'
' MODULE_ID {Subroutines.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' This sample demonstrates how to create an existing ground profile and profile view.
'
' Notes: 1. XML path is hard coded to the sample directory of the
'           Civil 2010 install, so it needs to be modified if the
'           the sample directory structure changes.
'        2. Global variables declared in ApplicationModule
'
Sub PerformProfileDemonstration()
    Dim oAlignment As AeccAlignment
    
    ' Always get the objects again since MDI is supported.
    If (GetBaseCivilObjects() = False) Then
        MsgBox "Error accessing top civil objects."
        Exit Sub
    End If

    If (CreateSurfaceByImport() = False) Then
        MsgBox "Error attempting to create a TIN surface from " & SURFACE_NAME & ".xml."
        Exit Sub
    End If
    
    If (CreateSite() = False) Then
        MsgBox "Error creating a site."
        Exit Sub
    End If

    If (CreateAlignmentByLayout(oAlignment) = False) Then
        MsgBox "Error creating an alignment."
        Exit Sub
    End If

    If (CreateProfile(oAlignment) = False) Then
        MsgBox "Error creating an existing ground profile."
        Exit Sub
    End If

    If (CreateProfileView(oAlignment) = False) Then
        MsgBox "Error creating a profile view."
        Exit Sub
    End If
    
    g_oCivilApp.ZoomExtents
End Sub

Attribute VB_Name = "Surface"
'
' MODULE_ID {Surface.bas}
' {ProfileSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

'
' Create a surface from data in an XML file.  The surface
' name comes from a global constant, so other functions
' can access the surface directly by name.
'
' NOTE: Notice the hard-coded path that needs to be modified
' if the file is in a different location.
'
Public Function CreateSurfaceByImport() As Boolean
    Dim oSurfaces As AeccSurfaces
    Set oSurfaces = g_oDocument.Surfaces
    If (oSurfaces Is Nothing) Then
        Debug.Print "Error: " & Err.Description
        Err.Clear
        CreateSurfaceByImport = False
        Exit Function
    End If

    Dim oSurface As AeccSurface
    Dim sXmlFileName As String
    On Error Resume Next
    Set oSurface = oSurfaces.Item(SURFACE_NAME)
    On Error GoTo 0
    If (oSurface Is Nothing) Then
        sXmlFileName = g_oCivilApp.Path & "\Sample\Civil 3D API\Vba\SurfacePoints\" & SURFACE_NAME & ".xml"
        On Error Resume Next
        Set oSurface = oSurfaces.ImportXML(sXmlFileName)
        On Error GoTo 0
        If (oSurface Is Nothing) Then
            Debug.Print "Error during loading XML file: " & vbNewLine & Err.Description
            CreateSurfaceByImport = False
            Err.Clear
        End If
    End If
    ThisDrawing.Application.ZoomExtents
    
    CreateSurfaceByImport = True
End Function
