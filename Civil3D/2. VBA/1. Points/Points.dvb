Attribute VB_Name = "GlobalVars"
Option Explicit

Public g_oCivilApp As AeccApplication       'Civil3D 어플리케이션 객체 전역 변수 선언
Public g_oDocument As AeccDocument  '도면 객체 변수 선언
Public g_oDatabase As AeccDatabase      '데이터베이스 객체 변수 선언

' 위 세개 전역 변수를 설정하는 GetGlobalCivilObjects() 함수를 만든다.
'
Function GetGlobalCivilObjects() As Boolean
    Dim oAcadApp As AcadApplication
    Set oAcadApp = ThisDrawing.Application
    ' Civil3D 버전 번호를 주의해야 한다. 여기서 번호 10은 Civil3d 2013 버전 객체이다.
    Const sAppName = "AeccXUiLand.AeccApplication.10.0"
    Set g_oCivilApp = oAcadApp.GetInterfaceObject(sAppName)
    If (g_oCivilApp Is Nothing) Then
        MsgBox "Error creating " & sAppName & ", exit."
        GetGlobalCivilObjects = False
        Exit Function
    End If
    Set g_oDocument = g_oCivilApp.ActiveDocument
    Set g_oDatabase = g_oDocument.Database
    GetGlobalCivilObjects = True            '성공적으로 설정하였으면 True를 리턴한다.
End Function

Attribute VB_Name = "Points"
Public Function EnumExistingPoints() As Boolean
    If (GetGlobalCivilObjects() = False) Then       ' 이 함수 실행과 관련된 전역 변수 설정
        MsgBox "Error accessing root objects."
        Exit Function
    End If

    Dim oPoints As AeccPoints
    Set oPoints = g_oDocument.Points
    
    ' 도면 객체의 Points 컬렉션에 포인트 3개 추가
    Dim lCountAdded As Long
    Const NUM_LOCATIONS As Long = 3
' 3개 포인트의 X, Y, Z 값 넣을 9개 실수변수 선언
    Dim dLocations(0 To (3 * NUM_LOCATIONS) - 1) As Double
    dLocations(0) = 4927: dLocations(1) = 3887: dLocations(2) = 150
    dLocations(3) = 5101: dLocations(4) = 3660: dLocations(5) = 250
    dLocations(6) = 5144: dLocations(7) = 3743: dLocations(8) = 350
    lCountAdded = oPoints.AddMultiple(NUM_LOCATIONS, dLocations, 0)
    
    Dim i As Long
    Dim avgEasting As Double        ' 동쪽 좌표 평균값 변수
    Dim avgNorthing As Double       ' 북쪽 좌표 평균값 변수
    Dim avgElevation As Double      ' 높이 평균값 변수

    Dim oPoint As AeccPoint
    For Each oPoint In oPoints      ' 루프를 돌며, 각 평균값 변수 누적
        avgEasting = avgEasting + oPoint.Easting
        avgNorthing = avgNorthing + oPoint.Northing
        avgElevation = avgElevation + oPoint.Elevation
    Next
    avgEasting = avgEasting / oPoints.Count         ' 포인트 개수로 누적 변수값을 나눔
    avgNorthing = avgNorthing / oPoints.Count
    avgElevation = avgElevation / oPoints.Count
    MsgBox "Average easting: " & avgEasting & vbNewLine & "Average northing: " & avgNorthing & vbNewLine & "Average elevation: " & avgElevation & vbNewLine & "Number of points: " & oPoints.Count      ' 결과값을 메시지로 표시
    EnumExistingPoints = True
End Function ' enumExistingPoints
