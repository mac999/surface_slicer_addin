Attribute VB_Name = "Alignment"
'
' MODULE_ID {Alignment.bas}
' {AlignmentSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit

' Note that this sample requires the user to specify a new
' drawing, such as _Autodesk Civil 3D (Imperial) NCS Extended.dwt
' so that there are predefined tick symbols and blocks that we can
' use, and so the text has a size we can actually see.


'
' Creates an alignment based on the coordinates of a lightweight
' polyline.
'
Public Function CreateAlignmentsByLWPolyline() As Boolean
    Dim i As Integer

    ' Alignments must be placed in a site, so we need to create a
    ' site first.
    If (CreateSite = False) Then
        CreateAlignmentsByLWPolyline = False
        Exit Function
    End If
    Dim oAlignments As AeccAlignments
    Set oAlignments = GetSite().Alignments
    
    ' This alignment will be based on a lightweight (2D) polyline
    ' entity.  Make a polyline and get its object ID.
    Dim dObjId As Long
    dObjId = CreateLWPolyline()
    If (dObjId = 0) Then
        Debug.Print "Error creating a polyline."
        CreateAlignmentsByLWPolyline = False
        Exit Function
    End If

    ' Create a new alignment style.  We need one before we
    ' create an alignment.
    If (CreateAlignmentStyle(ALIGNMENT_STYLE_NAME) = False) Then
        CreateAlignmentsByLWPolyline = False
        Exit Function
    End If

    ' An alignment also needs an alignment label style set.
    ' We will call a function that creates a new one and
    ' returns its name.
    If (CreateAlignmentLabelStyleSet(ALIGNMENT_LABEL_STYLE_SET_NAME) = False) Then
        CreateAlignmentsByLWPolyline = False
        Exit Function
    End If
    
    Dim oAlignment As AeccAlignment
    Set oAlignment = oAlignments.AddFromPolyline(ALIGNMENT_NAME, "0", dObjId, _
        ALIGNMENT_STYLE_NAME, ALIGNMENT_LABEL_STYLE_SET_NAME, True, True)

    If (oAlignment Is Nothing) Then
        Debug.Print "Error: " & Err.Description & " - " & Err.Number
        Err.Clear
        ThisDrawing.Application.ZoomExtents
        CreateAlignmentsByLWPolyline = False
        Exit Function
    End If
    
    ' See how many entities are in the alignment.
    Debug.Print "Number of Entities: "; oAlignment.Entities.Count
    
    ' Demonstration of looping through all
    ' alignment entities and getting a
    ' reference to each one using the correct
    ' type.
    For i = 0 To oAlignment.Entities.Count - 1
        Select Case (oAlignment.Entities.Item(i).Type)
            Case aeccTangent
                Dim oTangent As AeccAlignmentTangent
                Set oTangent = oAlignment.Entities.Item(i)
            Case aeccArc
                Dim oArc As AeccAlignmentArc
                Set oArc = oAlignment.Entities.Item(i)
            Case aeccSpiral
                Dim oSpiral As AeccAlignmentSpiral
                Set oSpiral = oAlignment.Entities.Item(i)
            Case aeccSpiralCurveSpiralGroup
                Dim oSCSGroup As AeccAlignmentSCSGroup
                Set oSCSGroup = oAlignment.Entities.Item(i)
            Case aeccSpiralTangentSpiralGroup
                Dim oSTSGroup As AeccAlignmentSTSGroup
                Set oSTSGroup = oAlignment.Entities.Item(i)
            Case aeccSpiralTangentGroup
                Dim oSTGroup As AeccAlignmentSTGroup
                Set oSTGroup = oAlignment.Entities.Item(i)
            Case aeccTangentSpiralGroup
                Dim oTSGroup As AeccAlignmentTSGroup
                Set oTSGroup = oAlignment.Entities.Item(i)
            Case aeccSpiralCurveGroup
                Dim oSCGroup As AeccAlignmentSCGroup
                Set oSTGroup = oAlignment.Entities.Item(i)
            Case aeccCurveSpiralGroup
                Dim oCSGroup As AeccAlignmentCSGroup
                Set oCSGroup = oAlignment.Entities.Item(i)
        End Select
    Next i
    
    ' Get station information
    Dim oAStations As AeccAlignmentStations
    Set oAStations = oAlignment.GetStations(aeccAll, 30, 10)
    Debug.Print "# of stations: " & oAStations.Count
    
    g_oCivilApp.Update
    ThisDrawing.Application.ZoomExtents
    CreateAlignmentsByLWPolyline = True
End Function ' CreateAlignmentsByLWPolyline


'
' Create a lightweight polyline using some arbitrary coordinates.
' Add the line to the drawing and return the id of the line.
'
Public Function CreateLWPolyline() As Long
    Dim oPoly As AcadLWPolyline
    Dim dPoints(0 To 5) As Double

    dPoints(0) = 0: dPoints(1) = 600
    dPoints(2) = 600: dPoints(3) = 0
    dPoints(4) = 1200: dPoints(5) = 600
    Set oPoly = g_oAeccDatabase.ModelSpace.AddLightWeightPolyline(dPoints)
    CreateLWPolyline = oPoly.ObjectID
End Function


'
' Create a line using coordinates passed as parameters.  Add
' the line to the drawing and return the id of the line.
'
Public Function CreateLine(x1 As Double, y1 As Double, z1 As Double, x2 As Double, y2 As Double, z2 As Double) As Long
    Dim oLine As AcadLine
    Dim dPoint1(2) As Double
    Dim dPoint2(2) As Double

    dPoint1(0) = x1: dPoint1(1) = y1: dPoint1(2) = z1
    dPoint2(0) = x2: dPoint2(1) = y2: dPoint2(2) = z2
    Set oLine = g_oAeccDatabase.ModelSpace.AddLine(dPoint1, dPoint2)
    CreateLine = oLine.ObjectID
End Function


'
' Creates an alignment based on layout data.
'
Public Function CreateAlignmentsByLayout() As Boolean
    Dim i As Integer
    
    ' Alignments must be placed in a site, so we need to create a
    ' site first.
    If (CreateSite = False) Then
        CreateAlignmentsByLayout = False
        Exit Function
    End If
    Dim oAlignments As AeccAlignments
    Set oAlignments = GetSite().Alignments

    ' Create a new alignment style.  We need one before we
    ' create an alignment.
    If (CreateAlignmentStyle(ALIGNMENT_STYLE_NAME) = False) Then
        CreateAlignmentsByLayout = False
        Exit Function
    End If

    ' An alignment also needs an alignment label style set.
    ' We will call a function that creates a new one and
    ' returns its name.
    If (CreateAlignmentLabelStyleSet(ALIGNMENT_LABEL_STYLE_SET_NAME) = False) Then
        CreateAlignmentsByLayout = False
        Exit Function
    End If

    ' Add a blank alignment with our style sets to the
    ' collection of alignments.
    Dim oAlignment As AeccAlignment
    Set oAlignment = oAlignments.Add(ALIGNMENT_NAME, "0", ALIGNMENT_STYLE_NAME, ALIGNMENT_LABEL_STYLE_SET_NAME)
    If (oAlignment Is Nothing) Then
        Debug.Print "Error creating alignment: " & Err.Description & " - " & Err.Number
        Err.Clear
        ThisDrawing.Application.ZoomExtents
        CreateAlignmentsByLayout = False
        Exit Function
    End If

    ' Add layout entities to the currently empty alignment.
    Dim point1(0 To 2) As Double
    Dim point2(0 To 2) As Double
    Dim point3(0 To 2) As Double
    point1(0) = 200: point1(1) = 800: point1(2) = 0
    point2(0) = 600: point2(1) = 400: point2(2) = 0
    point3(0) = 1000: point3(1) = 800: point3(2) = 0
    
    Dim oAlignmentTangent As AeccAlignmentTangent
    Set oAlignmentTangent = oAlignment.Entities.AddFixedLine1(point1, point2)
    Dim oAlignmentArc As AeccAlignmentArc
    Set oAlignmentArc = oAlignment.Entities.AddFloatingCurve6(oAlignmentTangent.Id, point3)

    ' Set the speeds at certain stations.
    Dim oDesignSpeed As AeccDesignSpeed
    Set oDesignSpeed = oAlignment.DesignSpeeds.Add(0#) ' Station 0 + 00.00
    oDesignSpeed.Value = 45
    oDesignSpeed.Comment = "Straightaway"
    Set oDesignSpeed = oAlignment.DesignSpeeds.Add(430#) ' Station 4 + 30.00
    oDesignSpeed.Value = 30
    oDesignSpeed.Comment = "Start of curve"
    Set oDesignSpeed = oAlignment.DesignSpeeds.Add(1427.131) ' Station 14 + 27.131
    oDesignSpeed.Value = 35
    oDesignSpeed.Comment = "End of curve"

    ' If we were to label major stations placed every 100 units
    ' and minor stations placed every 20, how many labels would
    ' this alignment have?
    Dim oAlignmentStations As AeccAlignmentStations
    Set oAlignmentStations = oAlignment.GetStations(aeccAll, 100#, 20#)
    Debug.Print "# of labels: " & oAlignmentStations.Count
    
    ' Report on the location of all major stations, using
    ' the displacement we used to create the station labels.
    For i = 0 To oAlignmentStations.Count - 1
        If (oAlignmentStations.Item(i).Type = aeccMajor) Then
            Dim j As Integer
            Dim x As Integer
            Dim y As Integer
            j = oAlignmentStations.Item(i).Station
            x = oAlignmentStations.Item(i).Easting
            y = oAlignmentStations.Item(i).Northing
            Debug.Print "Station " & j & " is at: " & x & ", " & y
        End If
    Next i
    
    ' Adjust how the station equations are numbered
    Dim oStationEquation As AeccStationEquation
    ' The "720" is the station value of the first station labeled
    ' The "80" is the distance along the alignment that the first new-equation station is placed
    '   up until this point, the stations are numbered zero based from the initial point.
    ' The second parameter is not used currently.
    Set oStationEquation = oAlignment.StationEquations.Add(80, 0, 720, aeccIncreasing)
    Set oAlignmentStations = oAlignment.GetStations(aeccEquation, 180#, 0#)
    Debug.Print "---"
    For i = 0 To oAlignmentStations.Count - 1
        Debug.Print "Station "; oAlignmentStations.Item(i).Station; " is at: "; oAlignmentStations.Item(i).Easting; ", "; oAlignmentStations.Item(i).Northing
    Next i


    ' Given a distance along the alignment, give the station equation.
    Debug.Print "Station 540 units from the start of the alignment is : "; oAlignment.GetStationStringWithEquations(540)
    Debug.Print
    
    ' Given an easting and northing, give the station closest to
    ' that point and the offset from the station to that point.
    ' Then draw a line from the location to that station.
    Dim dStation As Double
    Dim dOffset As Double
    Dim dNorth As Double
    Dim dEast As Double
    oAlignment.StationOffset 600, 600, dStation, dOffset
    Debug.Print "The station closest to 600,600 is : "; dStation; " with an offset of: "; dOffset
    Debug.Print
    oAlignment.PointLocation dStation, 0#, dEast, dNorth
    Call CreateLine(600, 600, 0#, dEast, dNorth, 0#)
    
    ' Add offset alignments to either side of the original
    ' alignment.
    oAlignment.Offset 10.5
    oAlignment.Offset -10.5

    ' Get distance between main alignment and all other
    ' alignments.
    Dim oCurAlignment As AeccAlignment
    Dim dDist As Double
    Dim dSourceStation As Double
    Dim dDestStation As Double
    dSourceStation = 216#
    'g_oCivilApp.Update
    ' Now that we added new alignments to the site, we
    ' have to re-get the collection of alignments.
    Set oAlignments = GetSite().Alignments
    Debug.Print "Measuring from station :"; dSourceStation
    ' Loop through all the alignments in the collection.
    For i = 0 To oAlignments.Count - 1
        Set oCurAlignment = oAlignments.Item(i)
        oAlignment.DistanceToAlignment dSourceStation, oCurAlignment, dDist, dDestStation
        ' The distance is 0 if we get the distance of an alignment
        ' to itself.
        If (dDist <> 0) Then
            Debug.Print oCurAlignment.Name; " - dist"; dDist; " at station: "; dDestStation
        End If
    Next i

    '''''''''''''''''''''''''''''''''''''''''''''''''''''''''''
    ' Adjust the superelevation settings for the alignment.
    ' This is used to adjust the bank of the road when a
    ' corridor is created using this alignment.
    
    ' This is no longer supported:
    ' Dim oSuperElevationData As AeccSuperElevationData
    ' Dim oSuperElevationElem As AeccSuperElevationDataElem

    ' Create a element at station 11+00.0.  A new default
    ' superelevation data element is assigned to our
    ' oSuperElevationElem variable.
    ' Set oSuperElevationData = oAlignment.SuperelevationData
    ' oSuperElevationData.Add 1100, oSuperElevationElem
    
    ' Specify the new percent grade for each road segment.
    'oSuperElevationElem.SegmentCrossSlope(aeccSuperLeftOutShoulderCrossSlope) = 0.05
    'oSuperElevationElem.SegmentCrossSlope(aeccSuperLeftOutLaneCrossSlope) = 0.02
    'oSuperElevationElem.SegmentCrossSlope(aeccSuperLeftInLaneCrossSlope) = 0.01
    'oSuperElevationElem.SegmentCrossSlope(aeccSuperLeftInShoulderCrossSlope) = 0.03
    'oSuperElevationElem.SegmentCrossSlope(aeccSuperRightInShoulderCrossSlope) = 0.03
    'oSuperElevationElem.SegmentCrossSlope(aeccSuperRightInLaneCrossSlope) = 0.01
    'oSuperElevationElem.SegmentCrossSlope(aeccSuperRightOutLaneCrossSlope) = 0.02
    'oSuperElevationElem.SegmentCrossSlope(aeccSuperRightOutShoulderCrossSlope) = 0.05
    'oSuperElevationElem.TransPointType = aeccSuperManual
    'oSuperElevationElem.TransPointDesc = "Manual adjustment"
    'oSuperElevationElem.RawStation = 1100
    
    ' Get all superelevation data.
    
    'Debug.Print
    'Debug.Print "Superelevations"
    'Debug.Print "---------------"
    
    'For Each oSuperElevationElem In oAlignment.SuperelevationData
    '    Debug.Print "At station: "; oSuperElevationElem.RawStation
    '    Debug.Print "  Right Out Shoulder Slope :"; oSuperElevationElem.SegmentCrossSlope(aeccSuperRightOutShoulderCrossSlope)
    '    Debug.Print "  Right Out Lane Slope     :"; oSuperElevationElem.SegmentCrossSlope(aeccSuperRightOutLaneCrossSlope)
    '    Debug.Print "  Right In Lane Slope      :"; oSuperElevationElem.SegmentCrossSlope(aeccSuperRightInLaneCrossSlope)
    '    Debug.Print "  Right In Shoulder Slope  :"; oSuperElevationElem.SegmentCrossSlope(aeccSuperRightInShoulderCrossSlope)
    '    Debug.Print "  Left In Shoulder Slope   :"; oSuperElevationElem.SegmentCrossSlope(aeccSuperLeftInShoulderCrossSlope)
    '    Debug.Print "  Left In Lane Slope       :"; oSuperElevationElem.SegmentCrossSlope(aeccSuperLeftInLaneCrossSlope)
    '    Debug.Print "  Left Out Lane Slope      :"; oSuperElevationElem.SegmentCrossSlope(aeccSuperLeftOutLaneCrossSlope)
    '    Debug.Print "  Left Out Shoulder Slope  :"; oSuperElevationElem.SegmentCrossSlope(aeccSuperLeftOutShoulderCrossSlope)
    '    Debug.Print "  Smoothing Curve Length: "; oSuperElevationElem.SmoothingCurveLength
    '    Debug.Print "  Description: "; oSuperElevationElem.TransPointDesc
    '    Debug.Print
    'Next
    
    ' Update the view and exit.
    g_oCivilApp.Update
    ThisDrawing.Application.ZoomExtents
    CreateAlignmentsByLayout = True
End Function ' createAlignmentsByLayout

Attribute VB_Name = "AlignmentLabelSet"
'
' MODULE_ID {AlignmentLabelSet.bas}
' {AlignmentSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit

'
' Create a style set for the alignment station labels, add
' it to the drawings list of style sets, and return its name
' so it can be used in creating a new alignment.  This style
' set will only modify the Major Station points.
'
Public Function CreateAlignmentLabelStyleSet(sLabelStyleSetName As String) As Boolean
    Dim i As Integer
    
    ' Add a new AeccAlignmentLabelStyleSet in the document's
    ' collection of AlignmentStyleSet objects, after first
    ' deleting any older version of the style set that might
    ' exist.
    Dim oAlignmentLabelStyleSet As AeccAlignmentLabelStyleSet
    Set oAlignmentLabelStyleSet = Nothing
    On Error Resume Next
    g_oDocument.AlignmentLabelStyleSets.Remove (sLabelStyleSetName)
    
    ' If there is an object using this style set, then it cannot
    ' be removed.  To cover those cases, we will just try using
    ' that style.
    Set oAlignmentLabelStyleSet = g_oDocument.AlignmentLabelStyleSets.Item(sLabelStyleSetName)
    On Error GoTo 0
    If (oAlignmentLabelStyleSet Is Nothing) Then
        Set oAlignmentLabelStyleSet = g_oDocument.AlignmentLabelStyleSets.Add(sLabelStyleSetName)
    Else
        ' Using the old style.  No need to make a new one.
        CreateAlignmentLabelStyleSet = True
        Exit Function
    End If
    
    ' Assign some alignment label styles.
    oAlignmentLabelStyleSet.Description = "This demonstrates many design elements."
    
    ' -------------------------------------------------------
    ' This section demonstrates how to set the major station
    ' label styles.  Minor station labels and geometry point
    ' labels are similarly structured.

    Dim oMajorStationStyle As AeccLabelMajorStationStyleSetItem
    Dim oLabelStyle As AeccLabelStyle
    Dim oLabelStyleTickComponent As AeccLabelStyleTickComponent
    Dim oLabelStyleLineComponent As AeccLabelStyleLineComponent
    Dim oLabelStyleTextComponent As AeccLabelStyleTextComponent
    Dim oLabelStyleBlockComponent As AeccLabelStyleBlockComponent

    ' Add to the document a generic AeccLabelStyle object for
    ' managing the style of major station labels.
    On Error Resume Next
    g_oDocument.AlignmentLabelStyles.MajorStationLabelStyles.Remove "Parallel with Line, Tick and Speed"
    Set oLabelStyle = g_oDocument.AlignmentLabelStyles.MajorStationLabelStyles.Item("Parallel with Line, Tick and Speed")
    On Error GoTo 0
    If (oLabelStyle Is Nothing) Then
        Set oLabelStyle = g_oDocument.AlignmentLabelStyles.MajorStationLabelStyles.Add("Parallel with Line, Tick and Speed")
    End If
    
    ' Add to the AeccLabelStyle object an object for managing
    ' the style of label ticks.  This style governs the
    ' properties of the tick mark placed at regular intervals
    ' (in this case, at every station).
    On Error Resume Next
    oLabelStyle.TickComponents.Remove "New Tick"
    Set oLabelStyleTickComponent = oLabelStyle.TickComponents.Item("New Tick")
    On Error GoTo 0
    If (oLabelStyleTickComponent Is Nothing) Then
        Set oLabelStyleTickComponent = oLabelStyle.TickComponents.Add("New Tick")
    End If
    ' Specify what kind of symbol is used for the tick.
    'ReadOnly Property
    'oLabelStyleTickComponent.BlockName = "AeccTickLine"
    oLabelStyleTickComponent.Lineweight.Value = 60 ' .60 mm
    oLabelStyleTickComponent.AlignWithObject = True ' perpendicular to alignment
    oLabelStyleTickComponent.Angle = 0# ' in degrees
    oLabelStyleTickComponent.Visibility = True

    ' Add to the AeccLabelStyle object an object for managing
    ' the style of label blocks.  This style governs arbitrary
    ' symbols.  We will use this to add a circular tick mark
    ' around the current line tick mark.
    On Error Resume Next
    oLabelStyle.BlockComponents.Remove "New Block"
    Set oLabelStyleBlockComponent = oLabelStyle.BlockComponents.Item("New Block")
    On Error GoTo 0
    If (oLabelStyleBlockComponent Is Nothing) Then
        Set oLabelStyleBlockComponent = oLabelStyle.BlockComponents.Add("New Block")
    End If
    'ReadOnly Property
    'oLabelStyleBlockComponent.BlockName = "AeccTickCircle"
    oLabelStyleBlockComponent.Visibility = True
    
    ' Add to the AeccLabelStyle object an object for managing
    ' the style of label lines.  This style governs lines placed
    ' at each station.  We will use this to point out which
    ' station each distantly located text label belongs to.
    On Error Resume Next
    oLabelStyle.LineComponents.Remove "New Line"
    Set oLabelStyleLineComponent = oLabelStyle.LineComponents.Item("New Line")
    On Error GoTo 0
    If (oLabelStyleLineComponent Is Nothing) Then
        Set oLabelStyleLineComponent = oLabelStyle.LineComponents.Add("New Line")
    End If
    oLabelStyleLineComponent.color = 40 ' orange-yellow
    oLabelStyleLineComponent.Angle = 2.094 ' radians, = 120 degrees
    oLabelStyleLineComponent.Length = 0.015 ' in whatever units are used in the drawing
    oLabelStyleLineComponent.StartPointXOffset = 0.005
    oLabelStyleLineComponent.StartPointYOffset = -0.005
    oLabelStyleLineComponent.Visibility = True
    
    ' Text componets specify what text is displayed at each station
    ' and managing how that text looks.  We will change what text is
    ' displayed, and move it under and to the side of each station
    ' anchor.
    
    ' Try using an already existing text component, as default
    ' label styles usually have one.
    On Error Resume Next
    Set oLabelStyleTextComponent = oLabelStyle.TextComponents.Item(0)
    On Error GoTo 0
    ' If a text component does not exist we will make a new one.
    If (oLabelStyleTextComponent Is Nothing) Then
        Set oLabelStyleTextComponent = oLabelStyle.TextComponents.Add("New Text")
    End If
    ' Curve the text to follow the curves of the alignment.
    oLabelStyleTextComponent.AllowToCurve = True
    oLabelStyleTextComponent.XOffset = 0.01
    oLabelStyleTextComponent.YOffset = -0.025 - oLabelStyleTextComponent.Height
    oLabelStyleTextComponent.Contents = "SPD=<[Design Speed(P0|RN|AP|Sn|OF)]>  STA=<[Station Value(Uft|FS|P2|RN|AP|Sn|TP|B2|EN|W0|OF)]>"
    oLabelStyleTextComponent.color = 253 ' light grey

    ' We have just finished adding a tick, a block, and a line
    ' to the AeccLabelStyle object, as well as modifying its
    ' text.  Now we will add the AeccLabelStyle object to the
    ' MajorStationLabelStyleSet, which is one of the style sets
    ' governing how the alignment is labeled.
    
    ' This specifies the distance along the alignment (in whatever
    ' units the drawing is using) to place each station.
    Dim dIncrement As Double
    dIncrement = 260#
    
    Set oMajorStationStyle = oAlignmentLabelStyleSet.MajorStationLabelStyleSet.Add(oLabelStyle, dIncrement)
    
    ' End of setting the major station label style.
    ' -------------------------------------------------------

    CreateAlignmentLabelStyleSet = True
End Function ' CreateAlignmentLabelStyleSet

Attribute VB_Name = "AlignmentStyle"
'
' MODULE_ID {AlignmentStyle.bas}
' {AlignmentSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit


'
' Create an alignment style with the given name,
' if no such style already exists.
'
Function CreateAlignmentStyle(sStyleName As String) As Boolean
    ' Make a new alignment style for our alignment if it
    ' has not been made already.  If there is a problem
    ' making the new style there is an error, so we trap
    ' that.
    Dim oAlignmentStyle As AeccAlignmentStyle
    
    ' See if a style by this name already exists.  If it
    ' does, we will use that style.
    On Error Resume Next
    Set oAlignmentStyle = g_oDocument.AlignmentStyles.Item(sStyleName)
    On Error GoTo 0
    ' If it does not, create a new alignment style by
    ' that name.
    If (oAlignmentStyle Is Nothing) Then
        On Error Resume Next
        Set oAlignmentStyle = g_oDocument.AlignmentStyles.Add(sStyleName)
        On Error GoTo 0
        If (oAlignmentStyle Is Nothing) Then
            MsgBox "Error setting an Alignment Style: " & Err.Description
            Err.Clear
            CreateAlignmentStyle = False
        End If
    End If
    
    ' Do not show direction arrows.  Styles do not govern
    ' the size of direction arrows - that is done in the
    ' ambient settings.
    oAlignmentStyle.ArrowDisplayStyle2d.Visible = False
    oAlignmentStyle.ArrowDisplayStyle3d.Visible = False
    ' Display curves using violet.
    oAlignmentStyle.CurveDisplayStyle2d.color = 200 ' violet
    oAlignmentStyle.CurveDisplayStyle3d.color = 200 ' violet
    oAlignmentStyle.CurveDisplayStyle2d.Visible = True
    oAlignmentStyle.CurveDisplayStyle3d.Visible = True
    ' Display straight sections in blue.
    oAlignmentStyle.LineDisplayStyle2d.color = 160 ' blue
    oAlignmentStyle.LineDisplayStyle3d.color = 160 ' blue
    oAlignmentStyle.LineDisplayStyle2d.Visible = True
    oAlignmentStyle.LineDisplayStyle3d.Visible = True

    oAlignmentStyle.EnableRadiusSnap = True
    
    g_oCivilApp.Update
    CreateAlignmentStyle = True
End Function

Attribute VB_Name = "BaseObjects"
'
' MODULE_ID {BaseObjects.bas}
' {AlignmentSample.dvb}
'
' Copyright {2003-2008} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit

Public g_oCivilApp As AeccApplication
Public g_oDocument As AeccDocument
Public g_oAeccDatabase As AeccDatabase
'
'
'
'
' Start Civil 3D and create Civil 3D document and database objects.
'
Function GetBaseCivilObjects() As Boolean
    Dim oApp As AcadApplication
    Set oApp = ThisDrawing.Application
    ' NOTE - Always specify the version number.
    Const sAppName = "AeccXUiLand.AeccApplication.10.0"
    Set g_oCivilApp = oApp.GetInterfaceObject(sAppName)
    If (g_oCivilApp Is Nothing) Then
        MsgBox "Error creating " & sAppName & ", exit."
        GetBaseCivilObjects = False
        Exit Function
    End If
    Set g_oDocument = g_oCivilApp.ActiveDocument
    Set g_oAeccDatabase = g_oDocument.Database
    GetBaseCivilObjects = True
End Function

Attribute VB_Name = "Globals"
'
' MODULE_ID {Globals.bas}
' {AlignmentSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'

Option Explicit


Global Const ALIGNMENT_NAME = "Sample alignment"
Global Const ALIGNMENT_STYLE_NAME As String = "Sample style"
Global Const ALIGNMENT_LABEL_STYLE_SET_NAME As String = "Sample label style set"
Global Const SITE_NAME As String = "Sample Site"

Attribute VB_Name = "Site"
'
' MODULE_ID {Site.bas}
' {AlignmentSample.dvb}
'
' Copyright {2003-2008} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit

'
' Create an site for the alignments.
'
Public Function CreateSite() As Boolean
    Dim oSites As AeccSites
    Set oSites = g_oDocument.Sites
    Dim oSite As AeccSite
    
    ' See if a site with the name SITE_NAME already exists.  If it
    ' does, use it.  If not, create a new site with that name.
    On Error Resume Next
    Set oSite = oSites.Item(SITE_NAME)
    On Error GoTo 0
    If (oSite Is Nothing) Then
        Set oSite = oSites.Add(SITE_NAME)
        If (oSite Is Nothing) Then
            Debug.Print "Error creating Site."
            CreateSite = False
            Exit Function
        End If
    End If
    CreateSite = True
End Function


'
' Return the a site object with the name that we use for all
' sites in this application.  If such a site does not exist,
' return Nothing.
'
Public Function GetSite() As AeccSite
    On Error Resume Next
    Set GetSite = g_oDocument.Sites.Item(SITE_NAME)
    On Error GoTo 0

    If (GetSite Is Nothing) Then
        Debug.Print "Error accessing site '" & SITE_NAME & "'."
        GetSite = Nothing
        Exit Function
    End If
End Function

Attribute VB_Name = "Subroutines"
'
' MODULE_ID {Subroutines.bas}
' {AlignmentSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit
'
' This sample demonstrates how to create an alignment
' by converting a light weight polyline using an alignment style
' and adding a major station label set.
'
' There is a dependency for an alignment object which is a site
' or a parcel. This sample creates a site first before creating
' an alignment.
'
' Note: Global variables declared in Application module.
'
'


Sub AlignmentFromPolyline()
    'always get the objects again since MDI is supported
    If (GetBaseCivilObjects = False) Then
        Exit Sub
    End If
    
    If (CreateAlignmentsByLWPolyline = False) Then
        Debug.Print "Error creating alignment object."
        Exit Sub
    End If
    
    g_oCivilApp.Update
End Sub


Sub AlignmentFromLayout()
    'always get the objects again since MDI is supported
    If (GetBaseCivilObjects = False) Then
        Exit Sub
    End If
    
    If (CreateAlignmentsByLayout = False) Then
        Debug.Print "Error creating alignment object."
        Exit Sub
    End If
    
    g_oCivilApp.Update
End Sub
