Attribute VB_Name = "Alignment"
'
' MODULE_ID {Alignment.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'
Public Function CreateAlignmentByLWPolyline(oAlignment As AeccAlignment) As Boolean
    ' Get the site that the alignment will be part of,
    ' and the collection of the site's alignments.
    Dim oSite As AeccSite
    Dim oAlignments As AeccAlignments
    Set oSite = GetSite()
    If (oSite Is Nothing) Then
        CreateAlignmentByLWPolyline = False
        Exit Function
    End If
    Set oAlignments = oSite.Alignments
    
    ' Create the polyline that the alignment will be based
    ' on.
    Dim objId As Long
    objId = CreateLWPolyline
    If (objId = 0) Then
        CreateAlignmentByLWPolyline = False
        Exit Function
    End If

    ' Set the style for the alignment.
    Dim oAlignmentStyle As AeccAlignmentStyle
    If (CreateAlignmentStyle(STYLE_NAME) = False) Then
        CreateAlignmentByLWPolyline = False
        Exit Function
    End If
    Set oAlignmentStyle = g_oDocument.AlignmentStyles.Item(STYLE_NAME)

    ' Set the label style for the alignment.
    Dim oLabelStyleSet As AeccAlignmentLabelStyleSet
    If (CreateAlignmentLabelStyleSet(LABEL_STYLE_SET_NAME) = False) Then
        CreateAlignmentByLWPolyline = False
        Exit Function
    End If
    Set oLabelStyleSet = g_oDocument.AlignmentLabelStyleSets.Item(LABEL_STYLE_SET_NAME)
    
    ' Create a simple alignment.
    On Error Resume Next
    Set oAlignment = oAlignments.AddFromPolyline(ALIGNMENT_NAME, "0", objId, oAlignmentStyle, oLabelStyleSet, True, True)
    On Error GoTo 0
    If (oAlignment Is Nothing) Then
        Debug.Print "Error alignment: " & Err.Description & " - " & Err.Number
        ThisDrawing.Application.ZoomExtents
        CreateAlignmentByLWPolyline = False
        Exit Function
    End If

    g_oCivilApp.Update
    CreateAlignmentByLWPolyline = True
End Function


'
' Create a polyline using five 2-D points and
' add the polyline to the drawing.
'
Public Function CreateLWPolyline() As Long
    Dim id As Long
    Dim oPoly As AcadLWPolyline
    Dim dPoints(0 To 9) As Double

    dPoints(0) = 3945: dPoints(1) = 3903
    dPoints(2) = 4389: dPoints(3) = 3576
    dPoints(4) = 4737: dPoints(5) = 4080
    dPoints(6) = 5095: dPoints(7) = 3572
    dPoints(8) = 5480: dPoints(9) = 3993
    Set oPoly = ThisDrawing.ModelSpace.AddLightWeightPolyline(dPoints)
    If (oPoly.ObjectID = 0) Then
        Debug.Print "Error creating a polyline."
        CreateLWPolyline = 0
        Exit Function
    End If

    CreateLWPolyline = oPoly.ObjectID
End Function

Attribute VB_Name = "AlignmentStyle"
'
' MODULE_ID {AlignmentStyle.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create an alignment style.  Make it simple because
' the focus is on the sections we will create along
' the alignment.
'
Function CreateAlignmentStyle(sStyleName As String) As Boolean
    Dim oAlignmentStyles As AeccAlignmentStyles
    Dim oAlignmentStyle As AeccAlignmentStyle
    
    ' Get the drawing's collection of alignment styles.
    On Error Resume Next
    Set oAlignmentStyles = g_oDocument.AlignmentStyles
    On Error GoTo 0
    If (oAlignmentStyles Is Nothing) Then
        Debug.Print "Error accessing collection of alignment styles: " & vbNewLine & Err.Description
        CreateAlignmentStyle = False
        Exit Function
    End If
    
    ' Get a particular style from the collection of styles.
    On Error Resume Next
    Set oAlignmentStyle = oAlignmentStyles.Item(sStyleName)
    On Error GoTo 0
    ' If the style does not exist, make a new one with that
    ' name.
    If (oAlignmentStyle Is Nothing) Then
        On Error Resume Next
        Set oAlignmentStyle = oAlignmentStyles.Add(sStyleName)
        On Error GoTo 0
        If (oAlignmentStyles Is Nothing) Then
            Debug.Print "Error trying to make a new alignment style: " & vbNewLine & Err.Description
            CreateAlignmentStyle = False
            Exit Function
        End If
    End If

    ' Create an uncluttered alignment so the sample lines
    ' are more visible.
    oAlignmentStyle.CurveExtensionsDisplayStylePlan.Visible = False
    oAlignmentStyle.CurveExtensionsDisplayStyleModel.Visible = False
    oAlignmentStyle.LineExtensionsDisplayStylePlan.Visible = False
    oAlignmentStyle.LineExtensionsDisplayStyleModel.Visible = False
    oAlignmentStyle.ArrowDisplayStylePlan.Visible = False
    oAlignmentStyle.ArrowDisplayStyleModel.Visible = False
    
    oAlignmentStyle.CurveDisplayStylePlan.color = 1 ' red
    oAlignmentStyle.CurveDisplayStylePlan.Visible = True
    oAlignmentStyle.LineDisplayStylePlan.color = 1 ' red
    oAlignmentStyle.LineDisplayStylePlan.Visible = True
    oAlignmentStyle.SpiralDisplayStylePlan.color = 1 ' red
    oAlignmentStyle.SpiralDisplayStylePlan.Visible = True
    
    g_oCivilApp.Update
    CreateAlignmentStyle = True
End Function


'
' Make an alignment label style set.  We just
' need the object to create the alignment - we
' will not actually be using labels on the
' alignment.
'
Function CreateAlignmentLabelStyleSet(sStyleSetName As String) As Boolean
    Dim oLabelStyleSet As AeccAlignmentLabelStyleSet
    
    On Error Resume Next
    Set oLabelStyleSet = g_oDocument.AlignmentLabelStyleSets.Item(sStyleSetName)
    On Error GoTo 0
    If (oLabelStyleSet Is Nothing) Then
        On Error Resume Next
        Set oLabelStyleSet = g_oDocument.AlignmentLabelStyleSets.Add(sStyleSetName)
        On Error GoTo 0
        If (oLabelStyleSet Is Nothing) Then
            CreateAlignmentLabelStyleSet = False
            Exit Function
        End If
    End If

    CreateAlignmentLabelStyleSet = True
End Function

Attribute VB_Name = "BaseObjects"
'
' MODULE_ID {BaseObjects.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
Public g_oCivilApp As AeccApplication
Public g_oDocument As AeccDocument
Public g_oAeccDb As AeccDatabase


'
' Start Civil 3D and create Civil 3D document and database objects.
'
Public Function GetBaseCivilObjects() As Boolean
    Dim oApp As AcadApplication
    Set oApp = ThisDrawing.Application
    ' NOTE - Always specify the version number.
    Const sAppName = "AeccXUiLand.AeccApplication.10.0"
    Set g_oCivilApp = oApp.GetInterfaceObject(sAppName)
    If g_oCivilApp Is Nothing Then
        MsgBox "Error creating " & sAppName & ", exit."
        GetBaseCivilObjects = False
        Exit Function
    End If
    Set g_oDocument = g_oCivilApp.ActiveDocument
    Set g_oAeccDb = g_oDocument.Database
    GetBaseCivilObjects = True
End Function

Attribute VB_Name = "Globals"
'
' MODULE_ID {Globals.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Global constants used throughout the application.
'
Global Const SURFACE_NAME As String = "EG"
Public Const SITE_NAME As String = "Sample site"
Global Const ALIGNMENT_NAME As String = "Alignment 01"
Global Const SAMPLE_LINE_GROUP_NAME As String = "Sample Line group 01"
Global Const SAMPLE_LINES_NAME1 As String = "Sample Line 01"
Global Const SAMPLE_LINES_NAME2 As String = "Sample Line 02"
Global Const SAMPLE_LINES_NAME3 As String = "Sample Line 03"
Global Const LAYER_NAME As String = "Section view Layer 01"
Global Const GROUP_PLOT_STYLE_NAME As String = "Group plot style 01"
Global Const SAMPLE_LINE_STYLE_NAME As String = "Sample Line style 01"
Global Const SAMPLE_LINE_LABEL_STYLE_NAME As String = "Sample Line label style 01"
Global Const MAJOR_OFFSET_LABEL_NAME As String = "Parallel with Tick and Line"
Global Const SAMPLE_LINE_SECTION_STYLE_NAME As String = "Sample Line section style 01"
Global Const SECTIONVIEW_STYLE_NAME As String = "Section View style 01"
Global Const SECTIONVIEW_NAME As String = "Section View " ' numbers are appended to this for each section view
Global Const SECTIONVIEW_BAND_STYLE_SET_NAME As String = "Section View band style set 01"
Global Const SECTIONVIEW_DATA_BAND_STYLE_NAME As String = " Section View data band style 01"
Global Const SHEET_STYLE_NAME As String = "Sheet Style 01"
Global Const LINE_STYLE As String = "Sample line 01"
Global Const BLOCK_STYLE As String = "Sample block 01"
Global Const TICK_STYLE As String = "Sample tick 01"


Global Const STYLE_NAME = "Sample alignment style 01"
Global Const LABEL_STYLE_SET_NAME = "Sample label style set 01"
Global Const PROFILE_STYLE_NAME = "Sample profile style 01"
Global Const PROFILE_VIEW_NAME = "Sample profile view 01"
Global Const PROFILE_VIEW_STYLE_NAME = "Sample profile view style 01"
Global Const PROFILE_LABEL_STYLE_SET_NAME = "Sample profile style set 01"
Global Const PROFILEVIEW_BAND_STYLE_NAME = "Sample band style set 01"
Global Const PROFILEVIEW_VERTICAL_BAND_STYLE_NAME = "Sample vertical band style 01"
Global Const LINE_STYLE2 = "Sample line 02"
Global Const BLOCK_STYLE2 = "Sample block 02"
Global Const TICK_STYLE2 = "Sample tick 02"
Global Const CREST_LABEL_STYLE_SET = "Sample crest label set 01"
Global Const STATION_LABEL_STYLE_SET = "Sample station label set 01"

Attribute VB_Name = "SampleLine"
'
' MODULE_ID {SampleLine.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Add a new empty group of sample lines to the alignment,
' with custom styles and label styles.
'
Public Function CreateSampleLineGroup(oAlignment As AeccAlignment) As Boolean
    ' Get the alignment's collection of sample line groups.
    Dim oSampleLineGroups As AeccSampleLineGroups
    On Error Resume Next
    Set oSampleLineGroups = oAlignment.SampleLineGroups
    On Error GoTo 0
    If (oSampleLineGroups Is Nothing) Then
        Debug.Print "Error getting Sample Line Groups collection"
        CreateSampleLineGroup = False
        Exit Function
    End If

    ' Create a plot style to be used by this sample line group.
    Dim oGroupPlotStyle As AeccGroupPlotStyle
    If (CreateGroupPlotStyle(GROUP_PLOT_STYLE_NAME) = False) Then
        MsgBox "Error creating profile style."
        CreateSampleLineGroup = False
        Exit Function
    End If
    Set oGroupPlotStyle = g_oDocument.GroupPlotStyles.Item(GROUP_PLOT_STYLE_NAME)

    ' Create a style to be used by this sample line group.
    Dim oSampleLineStyle As AeccSampleLineStyle
    If (CreateSampleLineStyle(SAMPLE_LINE_STYLE_NAME) = False) Then
        MsgBox "Error creating sample line style."
        CreateSampleLineGroup = False
        Exit Function
    End If
    Set oSampleLineStyle = g_oDocument.SampleLineStyles.Item(SAMPLE_LINE_STYLE_NAME)

    ' Create a label style to be used by this sample line group.
    Dim oSampleLineLabelStyle As AeccLabelStyle
    If (CreateSampleLineLabelStyle(SAMPLE_LINE_LABEL_STYLE_NAME) = False) Then
        MsgBox "Error creating sample line label style."
        CreateSampleLineGroup = False
        Exit Function
    End If
    Set oSampleLineLabelStyle = g_oDocument.SampleLineLabelStyles.Item(SAMPLE_LINE_LABEL_STYLE_NAME)


    ' Add a new group to hold the sample lines we will make.
    Dim oSampleLineGroup As AeccSampleLineGroup
    Set oSampleLineGroup = oSampleLineGroups.Add(SAMPLE_LINE_GROUP_NAME, LAYER_NAME, oGroupPlotStyle, oSampleLineStyle, oSampleLineLabelStyle)
    
    ' Now we add our surface to the list of surfaces that
    ' the group samples.
    Dim oSectionStyle As AeccSectionStyle
    ' Create a section style.
    If (CreateSectionStyle(SAMPLE_LINE_SECTION_STYLE_NAME) = False) Then
        MsgBox "Error creating sample line section style."
        CreateSampleLineGroup = False
        Exit Function
    End If
    Set oSectionStyle = g_oDocument.SectionStyles.Item(SAMPLE_LINE_SECTION_STYLE_NAME)
    
    Dim oSampledSurface As AeccSampledSurface
    Set oSampledSurface = oSampleLineGroup.SampledSurfaces.Add(g_oDocument.Surfaces.Item(SURFACE_NAME), oSectionStyle)
    oSampledSurface.UpdateMode = aeccSectionStateDynamic
    ' NOTE: If this is not set to True, no sections can be
    ' created from the sample lines.
    oSampledSurface.Sample = True ' Sample the surface at each sample line.
    
    
    ' This does the same as the above, but for all surfaces in
    ' the document.
    'oSampleLineGroup.SampledSurfaces.AddAllSurfaces oSectionStyle
    'Dim i As Integer
    'For i = 0 To oSampleLineGroup.SampledSurfaces.Count - 1
    '    oSampleLineGroup.SampledSurfaces.Item(i).Sample = True
    '    oSampleLineGroup.SampledSurfaces.Item(i).UpdateMode = aeccSectionStateDynamic
    'Next i
    
    
    ''''''''''''''''''''''''''''''''''''''''''''''''''''''
    ' We will use all three methods for adding sample lines
    ' to the collection of sample lines in our sample line
    ' group.
    
    
    ' (1) Add a sample line based on an AutoCAD lightweight
    ' polyline entity.  First, we create the polyline.
    Dim oPoly As AcadLWPolyline
    Dim dPoints(0 To 3) As Double

    ' Specify points that roughly, but are not quite perpendicular
    ' to and centered on the alignment.
    dPoints(0) = 4750: dPoints(1) = 4050
    dPoints(2) = 4770: dPoints(3) = 3950
    ' Substitute the following points for a demonstration of a
    ' sample line that does not cross an alignment.
    ' points(2) = 4800: points(3) = 4020
    Set oPoly = ThisDrawing.ModelSpace.AddLightWeightPolyline(dPoints)
    ' Now that we have a line, we can create a single sample
    ' line with those coordinates.
    Call oSampleLineGroup.SampleLines.AddByPolyline(SAMPLE_LINES_NAME1, oPoly, True)
    
    
    ' (2) Add a sample line based on a station.
    Dim dSwathWidthLeft As Double
    Dim dSwathWidthRight As Double
    Dim dStation As Double
    dSwathWidthRight = 45.5
    dSwathWidthLeft = 35.5
    dStation = 1100.5
    Call oSampleLineGroup.SampleLines.AddByStation(SAMPLE_LINES_NAME2, dStation, dSwathWidthLeft, dSwathWidthRight)
    
    ' (3) Add sample lines by specifying a range of stations.
    ' Specify where the sample lines will be drawn.
    Dim oStationRange As New AeccStationRange
    
    oStationRange.UseSampleIncrements = True
    oStationRange.SampleAtHighLowPoints = False
    oStationRange.SampleAtHorizontalGeometryPoints = False
    oStationRange.SampleAtSuperelevationCriticalStations = False
    oStationRange.SampleAtRangeEnd = True
    oStationRange.SampleAtRangeStart = True
    oStationRange.StartRangeAtAlignmentStart = False
    oStationRange.EndRangeAtAlignmentEnd = False
    oStationRange.StartRange = 10# ' we will only sample for 1000 units along the alignment
    oStationRange.EndRange = 1010#
    oStationRange.IncrementTangent = 200# ' sample every 200 units along straight lines
    oStationRange.IncrementCurve = 50# ' sample every 50 units along curved lines
    oStationRange.IncrementSpiral = 50# ' sample every 50 units along spiral lines
    oStationRange.SwathWidthLeft = 50# ' 50 units to the left of the station
    oStationRange.SwathWidthRight = 50# ' 50 units to the right of the station
    oStationRange.SampleLineDefaultDirection = aeccDirectionFromBaseAlignment
    Set oStationRange.SampleLineStyle = oSampleLineStyle
    
    ' Now that we specified a range of stations, we can create
    ' a series of sample lines based on these settings.
    oSampleLineGroup.SampleLines.AddByStationRange SAMPLE_LINES_NAME3, aeccSampleLineDuplicateActionOverwrite, oStationRange

    ' End of adding sample lines.
    ''''''''''''''''''''''''''''''''''''''''''''''''''''''

    
    CreateSampleLineGroup = True
End Function ' CreateSampleLineGroup

Attribute VB_Name = "SampleLineStyle"
'
' MODULE_ID {SampleLineStyle.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create the style for the plot group, which is needed
' to make a sample line view (that is, a group of graphs).
'
Public Function CreateGroupPlotStyle(sStyleName As String) As Boolean
    ' Create a new group plot style and add it to the
    ' drawing's collection of such styles.
    Dim oGroupPlotStyle As AeccGroupPlotStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.GroupPlotStyles.Remove (sStyleName)
    Set oGroupPlotStyle = g_oDocument.GroupPlotStyles.Item(sStyleName)
    On Error GoTo 0
    If (oGroupPlotStyle Is Nothing) Then
        On Error Resume Next
        Set oGroupPlotStyle = g_oDocument.GroupPlotStyles.Add(sStyleName)
        On Error GoTo 0
        If (oGroupPlotStyle Is Nothing) Then
            Debug.Print "Error creating an group plot style"
            CreateGroupPlotStyle = False
            Exit Function
        End If
    End If
    
    oGroupPlotStyle.AlignSectionViewsAbout = aeccGroupPlotAlignViewCenterLine
    oGroupPlotStyle.CellSize = aeccGroupPlotCellSizeUniform
    oGroupPlotStyle.GapBetweenPages = 1#
    'oGroupPlotStyle.MajorHorizontalGridRowSpace = 20.5
    'oGroupPlotStyle.MajorVerticalGridColumnSpace = 20.5
    oGroupPlotStyle.PlotBy = aeccGroupPlotAreaAll
    oGroupPlotStyle.PlotSectionViewsBy = aeccGroupPlotByRows
    oGroupPlotStyle.MaximumInRow = 18
    oGroupPlotStyle.StartCorner = aeccGroupPlotCornerUpperLeft
    
    ' ------------------------------------------------
    ' In this section, we will make a new sheet style.
    
    ' Create a new sheet style and add it to the drawing's
    ' collection of such styles.
    Dim oSheetStyle As AeccSheetStyle
    On Error Resume Next
    g_oDocument.SheetStyles.Remove (SHEET_STYLE_NAME)
    Set oSheetStyle = g_oDocument.SheetStyles.Item(SHEET_STYLE_NAME)
    On Error GoTo 0
    If (oSheetStyle Is Nothing) Then
        On Error Resume Next
        Set oSheetStyle = g_oDocument.SheetStyles.Add(SHEET_STYLE_NAME)
        On Error GoTo 0
        If (oSheetStyle Is Nothing) Then
            Debug.Print "Error creating a sheet style"
            CreateGroupPlotStyle = False
            Exit Function
        End If
    End If
    
    ' Set the sheet style properties.
    'oSheetStyle.SheetBorderDisplayStylePlan.color = 170 ' blue
    'oSheetStyle.MajorHorizontalGridDisplayStylePlan.color = 170 ' blue
        
    ' Finished making a new sheet style.
    ' ------------------------------------------------
    
    ' Assign out sheet style to the group plot style.
    oGroupPlotStyle.SheetStyle = oSheetStyle.Name
    
    CreateGroupPlotStyle = True
End Function ' CreateGroupPlotStyle


'
' Make a new style for the sample lines we will be
' creating.
'
Public Function CreateSampleLineStyle(sStyleName As String) As Boolean
    ' Create a new sample line style and add it to the
    ' drawing's collection of such styles.
    Dim oSampleLineStyle As AeccSampleLineStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SampleLineStyles.Remove (sStyleName)
    Set oSampleLineStyle = g_oDocument.SampleLineStyles.Item(sStyleName)
    On Error GoTo 0
    If (oSampleLineStyle Is Nothing) Then
        On Error Resume Next
        Set oSampleLineStyle = g_oDocument.SampleLineStyles.Add(sStyleName)
        On Error GoTo 0
        If (oSampleLineStyle Is Nothing) Then
            Debug.Print "Error creating an sample line style"
            CreateSampleLineStyle = False
            Exit Function
        End If
    End If

    oSampleLineStyle.VerticesDisplayStylePlan.color = 220 ' pink
    oSampleLineStyle.LineDisplayStylePlan.color = 190 ' purple
    
    CreateSampleLineStyle = True
End Function ' CreateSampleLineStyle


'
' Make a new style for the labels that will be used
' with the sample lines we will be creating.
'
Public Function CreateSampleLineLabelStyle(sStyleName As String) As Boolean
    ' Create a new sample line style and add it to the
    ' drawing's collection of such styles.
    Dim oOffsetLabelStyle As AeccLabelStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SampleLineLabelStyles.Remove (sStyleName)
    Set oOffsetLabelStyle = g_oDocument.SampleLineLabelStyles.Item(sStyleName)
    On Error GoTo 0
    If (oOffsetLabelStyle Is Nothing) Then
        On Error Resume Next
        Set oOffsetLabelStyle = g_oDocument.SampleLineLabelStyles.Add(sStyleName)
        On Error GoTo 0
        If (oOffsetLabelStyle Is Nothing) Then
            Debug.Print "Error creating an sample line style"
            CreateSampleLineLabelStyle = False
            Exit Function
        End If
    End If

    ' -------------------------------------------------------
    ' This section demonstrates how to set the major station
    ' label styles.  Minor offset labels, grade break labels,
    ' and segment labels are similarly structured.

    Dim oLabelStyleTickComponent As AeccLabelStyleTickComponent
    Dim oLabelStyleLineComponent As AeccLabelStyleLineComponent
    Dim oLabelStyleTextComponent As AeccLabelStyleTextComponent
    Dim oLabelStyleBlockComponent As AeccLabelStyleBlockComponent

    ' Add to the AeccLabelStyle object an object for managing
    ' the style of label ticks.  This style governs the
    ' properties of the tick mark placed at regular intervals
    ' (in this case, at every station).
    On Error Resume Next
    oOffsetLabelStyle.TickComponents.Remove TICK_STYLE
    Set oLabelStyleTickComponent = oOffsetLabelStyle.TickComponents.Item(TICK_STYLE)
    On Error GoTo 0
    If (oLabelStyleTickComponent Is Nothing) Then
        Set oLabelStyleTickComponent = oOffsetLabelStyle.TickComponents.Add(TICK_STYLE)
    End If
    ' Specify what kind of symbol is used for the tick.
    'oLabelStyleTickComponent.BlockName = "AeccTickLine"
    oLabelStyleTickComponent.Lineweight.Value = 60 ' .60 mm
    oLabelStyleTickComponent.AlignWithObject = True ' perpendicular to alignment
    oLabelStyleTickComponent.Angle = 0# ' in degrees
    oLabelStyleTickComponent.Visibility = True

    ' Add to the AeccLabelStyle object an object for managing
    ' the style of label blocks.  This style governs arbitrary
    ' symbols.  We will use this to add a circular tick mark
    ' around the current line tick mark.
    On Error Resume Next
    oOffsetLabelStyle.BlockComponents.Remove BLOCK_STYLE
    Set oLabelStyleBlockComponent = oOffsetLabelStyle.BlockComponents.Item(BLOCK_STYLE)
    On Error GoTo 0
    If (oLabelStyleBlockComponent Is Nothing) Then
        Set oLabelStyleBlockComponent = oOffsetLabelStyle.BlockComponents.Add(BLOCK_STYLE)
    End If
    'oLabelStyleBlockComponent.BlockName = "AeccTickCircle"
    oLabelStyleBlockComponent.Visibility = True
    
    ' Add to the AeccLabelStyle object an object for managing
    ' the style of label lines.  This style governs lines placed
    ' at each station.  We will use this to point out which
    ' station each distantly located text label belongs to.
    On Error Resume Next
    oOffsetLabelStyle.LineComponents.Remove LINE_STYLE
    Set oLabelStyleLineComponent = oOffsetLabelStyle.LineComponents.Item(LINE_STYLE)
    On Error GoTo 0
    If (oLabelStyleLineComponent Is Nothing) Then
        Set oLabelStyleLineComponent = oOffsetLabelStyle.LineComponents.Add(LINE_STYLE)
    End If
    oLabelStyleLineComponent.color = 40 ' orange-yellow
    oLabelStyleLineComponent.Angle = 2.094 ' radians, = 120 degrees
    oLabelStyleLineComponent.Length = 0.015 ' in whatever units are used in the drawing
    oLabelStyleLineComponent.StartPointXOffset = 0.0005
    oLabelStyleLineComponent.StartPointYOffset = 0
    oLabelStyleLineComponent.Visibility = True
    
    ' The major station label style automatically comes with a
    ' TextComponent named "Station".  Text componets like this
    ' one are for specifying what text is displayed at each
    ' station, and for managing how that text looks.  We will
    ' change what text is displayed, and move it under and to
    ' the side of each station anchor.
    Set oLabelStyleTextComponent = oOffsetLabelStyle.TextComponents.Item(0)
    ' Curve the text to follow the curves of the alignment.
    oLabelStyleTextComponent.AllowToCurve = True
    oLabelStyleTextComponent.XOffset = 0.01
    oLabelStyleTextComponent.YOffset = -0.015 - oLabelStyleTextComponent.Height
    oLabelStyleTextComponent.Contents = "Sta=<[Sample Line Raw Station(Uft|FS|P2|RN|AP|Sn|TP|B2|EN|W0|OF)]>"
    oLabelStyleTextComponent.color = 253 ' light grey

    ' We have just finished adding a tick, a block, and a line
    ' to the AeccLabelStyle object, as well as modifying its
    ' text.  Now we will add the AeccLabelStyle object to the
    ' MajorStationLabelStyleSet, which is one of the style sets
    ' governing how the alignment is labeled.
    'Debug.Print "count MajorStationLabelStyleSet: "; oAlignmentLabelStyleSet.MajorStationLabelStyleSet.Count
    'For i = 0 To oAlignmentLabelStyleSet.MajorStationLabelStyleSet.Count - 1
    '    If (oAlignmentLabelStyleSet.MajorStationLabelStyleSet.Item(i).Style.Name = oLabelStyle.Name) Then
    '        oAlignmentLabelStyleSet.MajorStationLabelStyleSet.Remove i
    '    End If
    'Next i
    'Dim dIncrement As Double
    '' This specifies the distance along the alignment (in whatever
    '' units the drawing is using) to place each station.
    'dIncrement = 900#
    '
    'Set oMajorStationStyle = oSampleLineLabelStyle.MajorStationLabelStyleSet.Add(oLabelStyle, dIncrement)
    'Set oMajorStationStyle = oAlignmentLabelStyleSet.MajorStationLabelStyleSet.Add(oLabelStyle, dIncrement)
    ' End of setting the major station label style.
    ' -------------------------------------------------------
    
    ' Set the default values for the style.
    g_oDocument.SampleLineLabelStyles.LabelStyleDefaults.LabelProperties.Visibility = True
    
    CreateSampleLineLabelStyle = True
End Function ' CreateSampleLineLabelStyle


'
' This style controls how a section is drawn.  The section
' is displayed as the data in each section view graph.
'
Public Function CreateSectionStyle(sStyleName As String) As Boolean
    ' Create a new sample line style and add it to the
    ' drawing's collection of such styles.
    Dim oSectionStyle As AeccSectionStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SectionStyles.Remove (sStyleName)
    Set oSectionStyle = g_oDocument.SectionStyles.Item(sStyleName)
    On Error GoTo 0
    If (oSectionStyle Is Nothing) Then
        On Error Resume Next
        Set oSectionStyle = g_oDocument.SectionStyles.Add(sStyleName)
        On Error GoTo 0
        If (oSectionStyle Is Nothing) Then
            Debug.Print "Error creating an sample line style"
            CreateSectionStyle = False
            Exit Function
        End If
    End If

    oSectionStyle.PointDisplayStyleSection.Visible = True
    oSectionStyle.PointDisplayStyleSection.color = 30 ' orange
    oSectionStyle.SegmentDisplayStyleSection.Visible = True
    oSectionStyle.SegmentDisplayStyleSection.color = 190 ' purple

    CreateSectionStyle = True
End Function ' CreateSectionStyle

Attribute VB_Name = "Section"
'
' MODULE_ID {Section.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Given an alignment with sample lines, create sections
' at each of the sample lines, determine the maximum
' altitude of each section, and make settings to each
' section object.
'
Public Function CreateSections(oAlignment As AeccAlignment) As Boolean
    ' Create a section for each sample line in the sample
    ' line group.
    oAlignment.SampleLineGroups.Item(0).CreateSectionsAtSampleLines
    
    Dim i As Integer
    Dim j As Integer
    Dim oSampleLineGroup As AeccSampleLineGroup
    Set oSampleLineGroup = oAlignment.SampleLineGroups.Item(0)
    
    For i = 0 To oSampleLineGroup.SampleLines.Count - 1
        Dim oSections As AeccSections
        Set oSections = oSampleLineGroup.SampleLines.Item(i).Sections

        For j = 0 To oSections.Count - 1
            Debug.Print "Max Elevation of "; oSections.Item(j).Name;
            Debug.Print ": "; oSections.Item(j).ElevationMax

            oSections.Item(j).DataType = aeccSectionDataTIN
            oSections.Item(j).StaticDynamic = aeccSectionStateDynamic
            ' We don't need to set .Style because it is already
            ' set for the entire group of sample lines when we
            ' created them.
        Next j
    Next i

    CreateSections = True
End Function

Attribute VB_Name = "SectionView"
'
' MODULE_ID {SectionView.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'


'
' Create the set of graphs displaying the surface
' cross section at each sample line along the
' alignment.
'
Public Function CreateSectionView(oAlignment As AeccAlignment) As Boolean
    Dim i As Integer
    Dim j As Integer

    ' Make a style for the section views we will soon
    ' be creating.
    Dim oSectionViewStyle As AeccSectionViewStyle
    If (CreateSectionViewStyle(SECTIONVIEW_STYLE_NAME) = False) Then
        MsgBox "Error creating section view style."
        CreateSectionView = False
        Exit Function
    End If
    Set oSectionViewStyle = g_oDocument.SectionViewStyles.Item(SECTIONVIEW_STYLE_NAME)


    ' Make a style for the band sets we wish to add to the
    ' section views.
    Dim oSectionViewBandStyleSet As AeccSectionViewBandStyleSet
    If (CreateSectionViewBandStyleSet(SECTIONVIEW_BAND_STYLE_SET_NAME) = False) Then
        MsgBox "Error creating section view style."
        CreateSectionView = False
        Exit Function
    End If
    Set oSectionViewBandStyleSet = g_oDocument.SectionViewBandStyleSets.Item(SECTIONVIEW_BAND_STYLE_SET_NAME)
    
    
    ' We have an alignment with sample lines.  Loop through
    ' all the sample line groups in the alignment.
    For i = 0 To oAlignment.SampleLineGroups.Count - 1
        Dim oSampleLines As AeccSampleLines
        Set oSampleLines = oAlignment.SampleLineGroups.Item(i).SampleLines
        
        ' Now loop through all the sample lines in the current
        ' sample line group.  For each sample line, we will add
        ' a section view at a unique location with a style and
        ' a data band that we defined earlier.
        Dim dStartX As Double
        Dim dStartY As Double
        Dim dOffsetRight As Double
        Dim dOffsetDown As Double
        dStartX = 6200#
        dStartY = 3600#
        dOffsetRight = 0
        dOffsetDown = 0
        For j = 0 To oSampleLines.Count - 1
            Dim oSectionView As AeccSectionView
            dOffsetRight = j * 300
            dOffsetDown = 900
            ' If we have already displayed half the section views,
            ' then create a new row.
            If (j > (oSampleLines.Count / 2)) Then
                dOffsetRight = (j - (oSampleLines.Count / 2)) * 300
                dOffsetDown = 400
            End If
            Dim dOriginPt(0 To 2) As Double
            dOriginPt(0) = dStartX + dOffsetRight ' to the right of the surface and previous section views
            dOriginPt(1) = dStartY + dOffsetDown ' slightly higher than the surface
            ' Create a section view with the specified style and bands.
            Set oSectionView = oSampleLines.Item(j).SectionViews.Add(SECTIONVIEW_NAME & CStr(j), LAYER_NAME, dOriginPt, oSectionViewStyle, oSectionViewBandStyleSet)
            ' Add another set of bands to the section view.
            Dim oSectionViewBandSetItem As AeccSectionViewBandSetItem
            Set oSectionViewBandSetItem = oSectionView.BandSet.Add(oSectionViewBandStyleSet.Item(0).BandStyle, oSampleLines.Item(j).Sections.Item(0), oSampleLines.Item(j).Sections.Item(0))
            ' Make sure that the new set is displayed on the bottom.
            oSectionViewBandSetItem.Location = aeccBandSetItemLocationBottom
            ' Delete the first set of bands.
            Call oSectionView.BandSet.Remove(0)
            Debug.Print "Gap:"; oSectionView.BandSet.Item(0).Gap
        Next j
    Next i

    CreateSectionView = True
End Function ' CreateSectionView

Attribute VB_Name = "SectionViewStyle"
'
' MODULE_ID {SectionViewStyle.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'


'
' Create a style for the section views.  This includes such
' features as the axes, the title, and the overall graph
' display.
'
Public Function CreateSectionViewStyle(sStyleName As String) As Boolean
    ' Create a new section view style and add it to the
    ' drawing's collection of such styles.
    Dim oSectionViewStyle As AeccSectionViewStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SectionViewStyles.Remove sStyleName
    Set oSectionViewStyle = g_oDocument.SectionViewStyles.Item(sStyleName)
    On Error GoTo 0
    If (oSectionViewStyle Is Nothing) Then
        On Error Resume Next
        Set oSectionViewStyle = g_oDocument.SectionViewStyles.Add(sStyleName)
        On Error GoTo 0
        If (oSectionViewStyle Is Nothing) Then
            Debug.Print "Error creating a section view style"
            CreateSectionViewStyle = False
            Exit Function
        End If
    End If

    ' Now set the style of the section view.
    
    Dim dOffset(0 To 2) As Double
    With oSectionViewStyle.TopAxis.MajorTickStyle
        .AnnotationDisplayStylePlan.color = 23 ' light brown
        .Height = 0.004 ' text height
        .AnnotationDisplayStylePlan.Visible = True ' show text
        .Interval = 15
        .Text = "<[Section View Point Offset(Um|P1|RN|Sn|AP|OF)]>m"
        .DisplayStylePlan.Visible = True ' show ticks
    End With
    With oSectionViewStyle.TopAxis.TitleStyle
        .DisplayStylePlan.color = 23 ' light brown
        .Height = 0.008 ' text height
        .Text = "Meters"
        dOffset(0) = 0#
        dOffset(1) = 0.02
        .Offset = dOffset
        .DisplayStylePlan.Visible = True
    End With
    
    oSectionViewStyle.BottomAxis.MajorTickStyle.Interval = 15
    oSectionViewStyle.BottomAxis.MajorTickStyle.Text = "<[Section View Point Offset(Uft|P1|RN|Sn|OF|AP)]>ft"
    oSectionViewStyle.BottomAxis.TitleStyle.Text = "Feet"
    dOffset(0) = 0#
    dOffset(1) = -0.02
    oSectionViewStyle.BottomAxis.TitleStyle.Offset = dOffset
    oSectionViewStyle.BottomAxis.TitleStyle.DisplayStylePlan.Visible = True
    
    oSectionViewStyle.GraphStyle.VerticalExaggeration = 4.1
    oSectionViewStyle.GraphStyle.GridStyle.GridsBelowDatum = 1
    oSectionViewStyle.GraphStyle.GridStyle.ClipVertical = False
    oSectionViewStyle.GraphStyle.GridStyle.ClipHorizontal = True
    '
    oSectionViewStyle.GraphStyle.GridStyle.MajorHorizontalDisplayStylePlan.Visible = True
    oSectionViewStyle.GraphStyle.GridStyle.MajorVerticalDisplayStylePlan.Visible = True
    oSectionViewStyle.GraphStyle.GridStyle.MinorHorizontalDisplayStylePlan.Visible = False
    oSectionViewStyle.GraphStyle.GridStyle.MinorVerticalDisplayStylePlan.Visible = False
    '
    dOffset(1) = 0.045
    oSectionViewStyle.GraphStyle.TitleStyle.Offset = dOffset
    oSectionViewStyle.GraphStyle.TitleStyle.Text = "EG at Station <[Section View Station(Uft|FS)]>" 'FS|P2|RN|Sn|OF|AP|B2|TP|EN|W0|DZY)]>"
    
    CreateSectionViewStyle = True
End Function ' CreateSectionViewStyle



'
'
'
Public Function CreateSectionViewBandStyleSet(sStyleName As String) As Boolean
    ' Create a new band style set and add it to the
    ' drawing's collection of such styles.
    Dim oSectionViewBandStyleSet As AeccSectionViewBandStyleSet
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SectionViewBandStyleSets.Remove sStyleName
    Set oSectionViewBandStyleSet = g_oDocument.SectionViewBandStyleSets.Item(sStyleName)
    On Error GoTo 0
    If (oSectionViewBandStyleSet Is Nothing) Then
        On Error Resume Next
        Set oSectionViewBandStyleSet = g_oDocument.SectionViewBandStyleSets.Add(sStyleName)
        On Error GoTo 0
        If (oSectionViewBandStyleSet Is Nothing) Then
            Debug.Print "Error creating a section view style"
            CreateSectionViewBandStyleSet = False
            Exit Function
        End If
    End If

    ' We will modify the style set by adding a band that
    ' has labels both for elevation at each major tick
    ' mark of the graph, and for grade changes at each
    ' grade break.
    '
    ' Remove any old section data band styles that might
    ' exist and create a new style.  It might be that the
    ' style is in use, and cannot be removed.  In that
    ' case, we will use the existing style.
    Dim oBandSectionDataStyle As AeccBandSectionDataStyle
    On Error Resume Next
    g_oDocument.SectionViewBandStyles.SectionDataBandStyles.Remove SECTIONVIEW_DATA_BAND_STYLE_NAME
    Set oBandSectionDataStyle = g_oDocument.SectionViewBandStyles.SectionDataBandStyles.Add(SECTIONVIEW_DATA_BAND_STYLE_NAME)
    On Error GoTo 0
    If (oBandSectionDataStyle Is Nothing) Then
        On Error Resume Next
        Set oBandSectionDataStyle = g_oDocument.SectionViewBandStyles.SectionDataBandStyles.Item(SECTIONVIEW_DATA_BAND_STYLE_NAME)
        On Error GoTo 0
        If (oBandSectionDataStyle Is Nothing) Then
            Debug.Print "Error trying to create a section band style."
            CreateSectionViewBandStyleSet = False
            Exit Function
        End If
    End If

    ' Now we can modify how profile views that use this
    ' style will appear.

    ' Display at every major grid line a tick mark and a label
    ' that shows the section elevation at that point.

    ' The major increment label style comes with a text
    ' component, so do not make a new AeccLabelStyleTextComponent
    ' object.  We just modify the existing "Item(0)".
    With oBandSectionDataStyle
        .MajorOffsetLabelDisplayStylePlan.color = 255 ' white
        .MajorOffsetLabelDisplayStylePlan.Visible = True
        .MajorOffsetTickDisplayStylePlan.color = 255 ' white
        .MajorOffsetTickDisplayStylePlan.Visible = True
    End With
    With oBandSectionDataStyle.MajorIncrementLabelStyle.TextComponents.Item(0)
        .Contents = "<[Section1 Elevation(Um|P3|RN|AP|Sn|OF)]>m"
        .color = 255 ' white
        .Visibility = True
        .YOffset = 0.015
    End With
    
    ' Display a red tick mark and a red label showing section
    ' elevation at each vertex endpoint in the sample line.
    ' Make the tick mark large, and only at the top of the
    ' band.
    With oBandSectionDataStyle
        .SampleLineVertexLabelDisplayStylePlan.color = 20 ' red-orange
        .SampleLineVertexLabelDisplayStylePlan.Visible = True
        .SampleLineVertexTickDisplayStylePlan.color = 20 ' red-orange
        .SampleLineVertexTickDisplayStylePlan.Visible = True
    End With
    With oBandSectionDataStyle.SampleLineVerticesLabelStyle.TextComponents.Item(0)
        .Contents = "<[Section1 Elevation(Um|P3|RN|AP|Sn|OF)]>m"
        .color = 20 ' red-orange
        .Visibility = True
        .YOffset = 0.008
    End With
    With oBandSectionDataStyle.SampleLineVerticesLabelStyle.TickStyle
        .IncrementSmallTicksAtMiddle = False
        .IncrementSmallTicksAtBottom = False
        .IncrementSmallTicksAtTop = True
        .SmallTicksAtTopSize = 0.015
    End With
    
    With oBandSectionDataStyle
        oBandSectionDataStyle.CenterLineLabelDisplayStylePlan.color = 220 ' pink (this color has priority)
        oBandSectionDataStyle.CenterLineLabelDisplayStylePlan.Visible = True
        oBandSectionDataStyle.CenterLineLabelStyle.TextComponents.Item(0).color = 255 ' white (this does not have priority - it will be pink)
        oBandSectionDataStyle.CenterLineLabelStyle.TextComponents.Item(0).Visibility = True
    End With

    ' Set the text style of the grade breaks in the data band.
    Dim oLabelStyleTextComponent As AeccLabelStyleTextComponent
    ' If a text component does not exist, we will just skip trying
    ' to set one.
    On Error GoTo EndGradeBand
    Set oLabelStyleTextComponent = oBandSectionDataStyle.GradeBreakLabelStyle.TextComponents.Item(0)
    On Error GoTo 0
    oLabelStyleTextComponent.Contents = "<[Section Segment Grade Change(FP|P2|RN|AP|Sn|OF)]>"
    oLabelStyleTextComponent.Visibility = True
    oLabelStyleTextComponent.color = 252 ' grey
    oLabelStyleTextComponent.BorderStyle.Visibility = True
    oLabelStyleTextComponent.YOffset = -0.015
    oBandSectionDataStyle.GradeBreakLabelDisplayStylePlan.Visible = True
    oBandSectionDataStyle.GradeBreakLabelDisplayStylePlan.color = 252 ' grey
    oBandSectionDataStyle.GradeBreakTickDisplayStylePlan.Visible = True
    oBandSectionDataStyle.GradeBreakTickDisplayStylePlan.color = 252 ' grey
EndGradeBand:
    '
    
    ' Hide all other data displayed in the data band.
    With oBandSectionDataStyle
        .CenterLineLabelDisplayStylePlan.Visible = False
        .CenterLineTickDisplayStylePlan.Visible = False
        .GradeBreakLabelDisplayStylePlan.Visible = False
        .GradeBreakTickDisplayStylePlan.Visible = False
        .MinorOffsetLabelDisplayStylePlan.Visible = False
        .MinorOffsetTickDisplayStylePlan.Visible = False
    End With
    
    ' Set the style of the data band borders and title.
    oBandSectionDataStyle.TitleBoxDisplayStylePlan.color = 10 ' red
    ' oBandSectionDataStyle.TitleBoxDisplayStylePlan.Linetype = "DOT"
    oBandSectionDataStyle.TitleBoxDisplayStylePlan.Visible = True
    
    oBandSectionDataStyle.TitleBoxTextDisplayStylePlan.color = 80 ' green
    oBandSectionDataStyle.TitleBoxTextDisplayStylePlan.Visible = True
    
    oBandSectionDataStyle.TitleStyle.Text = "Section Elevations" & vbNewLine & vbNewLine & "Grade Breaks"
    oBandSectionDataStyle.TitleStyle.OffsetFromBand = 0.01
    oBandSectionDataStyle.TitleStyle.TextBoxWidth = 0.18
    oBandSectionDataStyle.TitleStyle.TextHeight = 0.0121

    ' Finally, we add the section view data band style
    ' to the profile view style set we created earlier.
    Call oSectionViewBandStyleSet.Add(oBandSectionDataStyle)

    CreateSectionViewBandStyleSet = True
End Function ' CreateSectionViewBandStyleSet

Attribute VB_Name = "Site"
'
' MODULE_ID {Site.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create an AeccSite object.
'
Public Function CreateSite() As Boolean
    On Error Resume Next
    
    Dim oSites As AeccSites
    Set oSites = g_oDocument.Sites
    Dim oSite As AeccSite

    Set oSite = oSites.Item(SITE_NAME)
    If oSite Is Nothing Then
        Set oSite = oSites.Add(SITE_NAME)
        If oSite Is Nothing Then
            Debug.Print "Error creating " & SITE_NAME
            CreateSite = False
            Exit Function
        End If
    End If
    CreateSite = True
End Function
    

'
' Get our site object using the global site name
' if it exists.
'
Public Function GetSite() As AeccSite
    Dim oSites As AeccSites
    Dim oSite As AeccSite
    
    On Error Resume Next
    Set oSites = g_oDocument.Sites
    If (Not oSites Is Nothing) Then
        Set oSite = oSites.Item(SITE_NAME)
        If (oSite Is Nothing) Then
            Set GetSite = Nothing
        Else
            Set GetSite = oSite
        End If
    End If
End Function

Attribute VB_Name = "Subroutines"
'
' MODULE_ID {Subroutines.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
' This sample demonstrates how to create a section view from an existing
' ground profile along an alignment.
'
' Notes: 1. XML path is hard coded so needs to be modified if different.
'        2. Global variables declared in ApplicationModule and Globals module.
'
Sub PerformSectionDemonstration()
    Dim oAlignment As AeccAlignment
    
    ' Always get the objects again since MDI is supported
    If (GetBaseCivilObjects = False) Then
        MsgBox "Error accessing top civil objects."
        Exit Sub
    End If

    If (CreateSurfaceByImport = False) Then
        MsgBox "Error attempting to create a TIN surface from " & SURFACE_NAME & ".xml."
        Exit Sub
    End If
    
    If (CreateSite = False) Then
        MsgBox "Error creating a site."
        Exit Sub
    End If

    If (CreateAlignmentByLWPolyline(oAlignment) = False) Then
        MsgBox "Error creating an alignment."
        Exit Sub
    End If

    If (CreateSampleLineGroup(oAlignment) = False) Then
        MsgBox "Error creating sample line group."
        Exit Sub
    End If
    
    If (CreateSections(oAlignment) = False) Then
        MsgBox "Error creating sections."
        Exit Sub
    End If

    If (CreateSectionView(oAlignment) = False) Then
        MsgBox "Error creating a section view."
        Exit Sub
    End If
    
    g_oCivilApp.ZoomExtents
End Sub

Attribute VB_Name = "Surface"
'
' MODULE_ID {Surface.bas}
' {SectionSample.dvb}
'
' Copyright {2009} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'
' Create a surface using data from a .xml file.  The
' surface name is a global constant - other functions
' can access the surface through the name.
'
' NOTE: Notice the hard-coded path that needs to be modified
' if the file is in a different location.
'
Public Function CreateSurfaceByImport() As Boolean
    Dim oSurfaces As AeccSurfaces
    Set oSurfaces = g_oDocument.Surfaces
    If (oSurfaces Is Nothing) Then
        Debug.Print "Error: " & Err.Description
        Err.Clear
        CreateSurfaceByImport = False
        Exit Function
    End If

    Dim oSurface As AeccSurface
    Dim sXmlFileName As String
    On Error Resume Next
    Set oSurface = oSurfaces.Item(SURFACE_NAME)
    On Error GoTo 0
    If (oSurface Is Nothing) Then
        sXmlFileName = g_oCivilApp.Path & "\Sample\Civil 3D API\COM\Vba\SurfacePoints\" & SURFACE_NAME & ".xml"
        On Error Resume Next
        Set oSurface = oSurfaces.ImportXML(sXmlFileName)
        On Error GoTo 0
        If (oSurface Is Nothing) Then
            Debug.Print "Error during loading XML file: " & vbNewLine & Err.Description
            CreateSurfaceByImport = False
            Err.Clear
        End If
    End If
    ThisDrawing.Application.ZoomExtents
    
    ' Directly modify the style to include some contour information
    oSurface.Style.ContourStyle.MajorContourDisplayStylePlan.Visible = True
    oSurface.Style.ContourStyle.MajorContourDisplayStylePlan.color = 44 ' darkish yellow
    oSurface.Style.ContourStyle.MinorContourDisplayStylePlan.Visible = True
    oSurface.Style.ContourStyle.MinorContourDisplayStylePlan.color = 48 ' very dark yellow
    
    CreateSurfaceByImport = True
End Function
